;___________ Project-4.lsp - Улучшенная версия Project-2-02 _____________
; Версия: 4.2
; Дата: 2025
; Улучшения:
;   - Улучшенная обработка ошибок
;   - Более понятные имена переменных
;   - Расширенная документация
;   - Оптимизация производительности
;   - Поддержка типизации
;   - Улучшенная система отладки
;   - Trampoline Pattern для преобразования рекурсии в итерацию (v4.2)
;   - Защита от бесконечной рекурсии и переполнения стека (v4.2)

(?princ "\r[Project-4.2] - Loader") 


;===========================================================================
; ГЛОБАЛЬНЫЕ ПЕРЕМЕННЫЕ
;===========================================================================

(setq *Уровень-Рекурсии* 0)           ; Счетчик уровня рекурсии
(setq *Напечатать* 0)                  ; Счетчик для отладки
(setq *isDebug* t)                     ; Режим отладки (генерация debug1.lsp)
(setq *isGraf* nil)                    ; Печать графа выполнения
(setq *$Notifier* nil)                 ; ActiveX объект для доступа к данным
(setq *$VariableDatabase* nil)         ; База данных переменных
(setq *$AttrDatabase* nil)             ; База данных атрибутов
(setq *Seconds-L* 0.0)                 ; Время последнего события
(setq *Текущий-Элемент-Правила* nil)   ; Текущий элемент для Call_Правило

; Обнуление переменных логирования ошибок (Error.MD и Error.JSON)
(setq *Ошибка-Счетчик* 0)              ; Счетчик ошибок
(setq *Ошибка-Стек-Вызовов* nil)       ; Стек вызовов функций
(setq *Ошибка-Контекст* nil)           ; Контекст выполнения
(setq *Ошибка-История-JSON* nil)       ; История ошибок для JSON экспорта
(setq *log* nil)                       ; Текстовая строка с информацией о загруженных функциях (устанавливается через ?log)
; ВАЖНО: Переменная *log* устанавливается функцией ?log, а не через setq напрямую
; Формат: "L: lineCode FileNameOrSqlID defunLastName defunNextName " или "i: lineCode FileNameOrSqlID defunLastName "
; Использование: (?log "L: 38 Project-4.lsp Имя-Функции Следующая-Функция ")

; Очистка логов ошибок при загрузке Project-4.lsp
(if (boundp 'Ошибка-Очистить-Лог)
  (Ошибка-Очистить-Лог)
)

;===========================================================================
; TRAMPOLINE PATTERN - Управление рекурсией
;===========================================================================

(setq *Использовать-Trampoline* t)     ; Флаг использования Trampoline Pattern
(setq *Макс-Глубина-Рекурсии* 1000)    ; Максимальная глубина рекурсии
(setq *Стек-Вызовов* nil)              ; Стек для хранения вызовов (Trampoline)
(setq *История-Вызовов* nil)           ; История вызовов для обнаружения циклов

;===========================================================================
; CONTINUATION PATTERN - Глобальные переменные
;===========================================================================

(setq *Стек-Continuation* nil)           ; Стек сохраненных состояний
(setq *Счетчик-Continuation* 0)         ; Счетчик для ID continuation
(setq *Максимум-Continuation* 50)       ; Максимальное количество continuation

;===========================================================================
; СПИСКИ КОНФИГУРАЦИИ
;===========================================================================

; Прозрачные команды - выполняются последовательно по одному правилу
(setq *Список-Прозрачных-Команд* '(
  (Новый)
  (Определить-Переменные)
  (Анализ-Данных)
  (Соединить-Элементы)
))

; Общий список всех классов
(setq *Общий-Список-Классов* ())

; Порядок наследования классов
(setq *Список-Порядка-Наследования* '())

;===========================================================================
; ЭКСПЕРТНАЯ СИСТЕМА ПРАВИЛ (Expert System Rules)
;===========================================================================

; Система приоритетов правил (Salience)
(setq *Салютность-Правил* nil)              ; Список правил с приоритетами
(setq *Стратегия-Разрешения* 'Порядок-Списка) ; Текущая стратегия выбора правил

; Константы приоритетов
(setq *Приоритет-Высокий* 1000)             ; Высокий приоритет
(setq *Приоритет-Средний* 500)              ; Средний приоритет
(setq *Приоритет-Низкий* 100)               ; Низкий приоритет
(setq *Приоритет-По-Умолчанию* 0)           ; Приоритет по умолчанию

; Рабочая память (Working Memory)
(setq *Рабочая-Память* nil)                 ; Факты в рабочей памяти
(setq *Счетчик-Фактов* 0)                   ; Счетчик для уникальных ID фактов

; Состояние цикла вывода
(setq *Последнее-Состояние-Памяти* nil)     ; Для отслеживания изменений

;===========================================================================
; ФУНКЦИИ ОТЛАДКИ И ЛОГИРОВАНИЯ
;===========================================================================

(defun Print-IGraf (Элемент Mode / @Per @Per-1 iGraf iStr) ; -L105
  "Вывод графа выполнения для отладки"
  (?catch "i: 106 Print-IGraf Project-4.lsp " '; -L106
    (progn ; -L107
      (if (not (NULL *isGraf*)) ; -L108
        (progn ; -L109
          (cond ; -L110
            ((= mode 0) ; -L111
              (progn
                (?princ "\n")
                (?princ *Уровень-Рекурсии*)
                (setq iGraf *Уровень-Рекурсии* iStr "")
                (while (> iGraf 0) ; -L117
                  (?princ "\t")
                  (setq iGraf (- iGraf 1))
                ) ;end while L120
                (?princ "-->")
                (?princ (car Элемент))
                (setq @Per (nth 2 (cadr (cadr Элемент)))
                      @Per-End nil
                ) ;end setq L127
                (?princ "\t")
                (foreach @Per-1 @Per
                  (if (AND (NULL @Per-End) (/= @Per-1 '/)) ; -L132
                    (progn ; -L133
                      (?princ "[")
                      (?princ @Per-1)
                      (?princ "]")
                    ) ;end progn L137
                    (setq @Per-End t)
                  ) ;end if L139
                ) ;end foreach L140
                (?princ "\tУсловие:")
                (?princ (cddr (caar (cdr Элемент))))
              ) ;end progn L144
            ) ;end cond case L145
            ((= mode 1) (?princ "- Условие не выполнено"))
            ((= mode 2) (?princ "- Условие выполнено"))
            ((= mode 3) (progn (?princ "\n") (?princ Элемент)))
            ((= mode 4) ; -L150
              (if (/= (type (cadr Элемент)) 'LIST) ; -L151
                (progn ; -L152
                  (?princ "\n====== Результат =======")
                  (?princ "\t")
                  (?princ (cadr Элемент))
                ) ;end progn L156
              ) ;end if L157
            ) ;end cond case L158
          ) ;end cond L159
          (setq s (getvar "DATE"))
          (setq seconds1 (* 86400.0 (- s (fix s))))
          (?princ "Time:")
          (?princ (* (- seconds1 *Seconds-L*) 100))
          (setq *Seconds-L* seconds1)
        ) ;end progn L167
      ) ;end if L168
    ) ;end progn L107
  ) ;end ?catch L106
) ;end defun Print-IGraf L105
(?log "L: 182 Project-4.lsp Print-IGraf Инициализировать-Отладку ")

;===========================================================================
; ИНИЦИАЛИЗАЦИЯ ОТЛАДКИ
;===========================================================================

(defun Инициализировать-Отладку (/ CR-Debug) ; -L189
  "Инициализация системы отладки"
  (?catch "i: 190 Инициализировать-Отладку Project-4.lsp " '; -L190
    (progn ; -L191
      (setq CR-Debug (getint "\n Create-Debug? (1-Yes, 0-No): "))
      (if CR-Debug ; -L193
        (progn ; -L194
          (setq #1 (open (strcat "debug1" ".lsp") "w"))
          (close #1)
          (setq *isDebug* t)
        ) ;end progn L198
        (setq *isDebug* nil)
      ) ;end if L200
      CR-Debug
    ) ;end progn L191
  ) ;end ?catch L190
) ;end defun Инициализировать-Отладку L189
(?log "L: 205 Project-4.lsp Инициализировать-Отладку -> ")

; Вызов инициализации при загрузке (опционально)
; (Инициализировать-Отладку)


;===========================================================================
; ОСНОВНЫЕ ФУНКЦИИ СИСТЕМЫ КЛАССОВ
;===========================================================================

(defun -> (Данные Элемент Стек_Контекста / This ЭлементRet Список-Правил Список-Данных Ключ-Вызова) ; -L216
  "Вызов метода объекта с данными
  
  Параметры:
    Данные - объект в формате '(Имя-Класса (Список-Атрибутов))
    Элемент - имя вызываемого метода
    Стек_Контекста - список локальных переменных '((Параметр Значение))
  
  Возвращает: результат выполнения метода
  
  Поддерживает защиту от бесконечной рекурсии через проверку глубины
  и обнаружение циклических вызовов"
  
  (?catch "i: 217 -> Project-4.lsp " '; -L217
    (progn ; -L218
      ; Проверка глубины рекурсии
      (cond ; -L220
        ((> *Уровень-Рекурсии* *Макс-Глубина-Рекурсии*) ; -L221
          (progn ; -L222
            (?princ (strcat "\n[ОШИБКА] Превышена максимальная глубина рекурсии: " 
                           (itoa *Уровень-Рекурсии*) 
                           " (максимум: " 
                           (itoa *Макс-Глубина-Рекурсии*) ")"))
            (setq ЭлементRet nil)  ; Возврат nil при ошибке
          ) ;end progn L228
        ) ;end cond case L229
        (T ; -L230
          (progn ; -L231
            ; Проверка на циклические вызовы (если включен Trampoline)
            (if *Использовать-Trampoline* ; -L233
              (progn ; -L234
                (setq Ключ-Вызова (list (car Данные) Элемент))
                (if (member Ключ-Вызова *История-Вызовов*) ; -L237
                  (progn ; -L238
                    (if *isDebug* ; -L239
                      (?princ (strcat "\n[ПРЕДУПРЕЖДЕНИЕ] Обнаружен циклический вызов: " 
                                    (vl-symbol-name (car Данные)) " -> " 
                                    (vl-symbol-name Элемент)))
                    ) ;end if L243
                    (setq ЭлементRet nil)
                  ) ;end progn L245
                  (setq *История-Вызовов* (cons Ключ-Вызова *История-Вызовов*))
                ) ;end if L248
              ) ;end progn L234
            ) ;end if L233
            
            (if (NULL ЭлементRet) ; -L252
              (progn ; -L253
                (setq *Уровень-Рекурсии* (+ *Уровень-Рекурсии* 1))
    
                (Print-IGraf Элемент 3)
                
                ; Извлечение списка данных
                (setq Список-Данных (cadr Данные))
                (if (and Список-Данных (/= (type (nth 0 Список-Данных)) 'LIST)) ; -L261
                  (setq Список-Данных nil)
                ) ;end if L263
                
                ; Формирование контекста This
                (setq This (list 'This (list (list (reverse Список-Данных) (reverse Список-Правил)))))
                
                ; Поиск и выполнение метода
                (setq ЭлементRet (::Do-Poisk))
                
                ; Восстановление состояния
                (setq *Уровень-Рекурсии* (- *Уровень-Рекурсии* 1))
                (if *Использовать-Trampoline* ; -L274
                  (setq *История-Вызовов* (cdr *История-Вызовов*))
                ) ;end if L276
                
                (Print-IGraf ЭлементRet 4)
              ) ;end progn L253
            ) ;end if L252
          ) ;end progn L231
        ) ;end cond case L281
      ) ;end cond L282
      
      ; Возврат результата
      (if ЭлементRet ; -L285
        (cadr ЭлементRet)
        nil
      ) ;end if L288
    ) ;end progn L218
  ) ;end ?catch L217
) ;end defun -> L216
(?log "L: 367 Project-4.lsp -> => ")

(defun => (Элемент Стек_Контекста) ; -L325
  "Выполнение процедуры в текущем контексте This
  
  Параметры:
    Элемент - имя процедуры
    Стек_Контекста - список локальных переменных
  
  Возвращает: результат выполнения"
  (?catch "i: 326 => Project-4.lsp " '; -L326
    (progn ; -L327
      (cadr (#Subr=> Элемент Стек_Контекста))
    ) ;end progn L327
  ) ;end ?catch L326
) ;end defun => L325
(?log "L: 379 Project-4.lsp => #Subr=> ")

(defun #Subr=> (Элемент Стек_Контекста / !Стек) ; -L337
  "Внутренняя функция выполнения процедуры
  
  Поддерживает защиту от бесконечной рекурсии"
  
  (?catch "i: 338 #Subr=> Project-4.lsp " '; -L338
    (progn ; -L339
      ; Проверка глубины рекурсии
      (cond ; -L341
        ((> *Уровень-Рекурсии* *Макс-Глубина-Рекурсии*) ; -L342
          (progn ; -L343
            (?princ (strcat "\n[ОШИБКА] Превышена максимальная глубина рекурсии в #Subr=>: " 
                           (itoa *Уровень-Рекурсии*)))
            (setq ЭлементRet nil)
          ) ;end progn L347
        ) ;end cond case L348
        (T ; -L349
          (progn ; -L350
            (setq !Стек This)  ; Сохранение текущего контекста
            (setq *Уровень-Рекурсии* (+ *Уровень-Рекурсии* 1))
            (Print-IGraf Элемент 3)
            
            (setq ЭлементRet nil)
            
            (!Добавить-Переменные Стек_Контекста)
            (::Do-Poisk)
            
            (setq *Уровень-Рекурсии* (- *Уровень-Рекурсии* 1))
            (setq This !Стек)  ; Восстановление контекста
            
            (Print-IGraf ЭлементRet 4)
          ) ;end progn L350
        ) ;end cond case L363
      ) ;end cond L364
      
      ЭлементRet
    ) ;end progn L339
  ) ;end ?catch L338
) ;end defun #Subr=> L337
(?log "L: 422 Project-4.lsp #Subr=> ::-> ")

(defun ::-> (Данные Элемент Стек_Контекста / This ЭлементRet Список-Правил Список-Данных) ; -L380
  "Внутренний вызов метода с обработкой поиска в иерархии классов
  
  Поддерживает защиту от бесконечной рекурсии"
  
  (?catch "i: 381 ::-> Project-4.lsp " '; -L381
    (progn ; -L382
      ; Проверка глубины рекурсии
      (cond ; -L384
        ((> *Уровень-Рекурсии* *Макс-Глубина-Рекурсии*) ; -L385
          (progn ; -L386
            (?princ (strcat "\n[ОШИБКА] Превышена максимальная глубина рекурсии в ::->: " 
                           (itoa *Уровень-Рекурсии*)))
            (setq ЭлементRet nil)
          ) ;end progn L390
        ) ;end cond case L391
        (T ; -L392
          (progn ; -L393
            (setq *Уровень-Рекурсии* (+ *Уровень-Рекурсии* 1))
            (Print-IGraf Элемент 3)
            
            (setq ЭлементRet nil)
            
            (if (/= (car Данные) 'This) ; -L400
              (progn ; -L401
                (Poisk Данные)  ; Поиск атрибутов и формирование списка данных
                (if (NULL ЭлементRet) ; -L404
                  (progn ; -L405
                    (setq This (list 'This (list (list (reverse Список-Данных) (reverse Список-Правил)))))
                    (!Добавить-Переменные Стек_Контекста)
                    (::Do-Poisk)
                  ) ;end progn L409
                ) ;end if L410
              ) ;end progn L401
              (progn ; -L412
                (setq This Данные)
                (!Добавить-Переменные Стек_Контекста)
                (::Do-Poisk)
              ) ;end progn L412
            ) ;end if L415
            
            (setq *Уровень-Рекурсии* (- *Уровень-Рекурсии* 1))
            (Print-IGraf ЭлементRet 4)
          ) ;end progn L393
        ) ;end cond case L420
      ) ;end cond L421
      
      (if ЭлементRet ; -L424
        (cadr ЭлементRet)
        nil
      ) ;end if L427
    ) ;end progn L382
  ) ;end ?catch L381
) ;end defun ::-> L380
(?log "L: 492 Project-4.lsp ::-> ::Do-Poisk ")

;===========================================================================
; ПОИСК И ВЫПОЛНЕНИЕ МЕТОДОВ
;===========================================================================

(defun ::Do-Poisk (/ DClass) ; -L454
  "Поиск метода в иерархии классов"
  (?catch "i: 455 ::Do-Poisk Project-4.lsp " '; -L455
    (progn ; -L456
      (cond ; -L457
        ; Поиск в стеке контекста
        ((setq ЭлементRet (assoc Элемент (cadr (cadr This)))) ; -L459
         ()
        ) ;end cond case L461
        ; Поиск в атрибутах
        ((setq ЭлементRet (assoc Элемент (caaadr This))) ; -L463
         ()
        ) ;end cond case L465
        ; Поиск в правилах классов
        ((setq ЭлементRet (Найти-Правило Элемент (cadr (caadr This)))) ; -L467
         ()
        ) ;end cond case L469
        ; Поиск через ActiveX интерфейс
        ((and (NOT (NULL *$Notifier*)) ; -L471
              (vlax-property-available-p *$Notifier* Элемент)) ; -L472
         (setq ЭлементRet (list Элемент (vlax-get-property *$Notifier* Элемент)))
        ) ;end and L474
      ) ;end cond L475
      ЭлементRet
    ) ;end progn L456
  ) ;end ?catch L455
) ;end defun ::Do-Poisk L454
(?log "L: 523 Project-4.lsp ::Do-Poisk Do-Poisk ")

(defun Do-Poisk ()
  "Альтернативная функция поиска (для обратной совместимости)"
  (?catch "i: 481 Do-Poisk Project-4.lsp " '; -L481
    (progn ; -L482
      (::Do-Poisk)
    ) ;end progn L482
  ) ;end ?catch L481
) ;end defun Do-Poisk L481
(?log "L: 529 Project-4.lsp Do-Poisk Poisk-Итеративный ")

;===========================================================================
; TRAMPOLINE PATTERN - Итеративные версии функций
;===========================================================================

(defun Poisk-Итеративный (#Данные / ; -L447
                          #Стек-Задач          ; Стек задач для обработки
                          #Текущие-Данные      ; Данные текущей задачи
                          #Атом                ; Текущий атом
                          #Тип-Элемента        ; Тип текущего элемента
                         )
  "Итеративный поиск правила или атрибута в данных (Trampoline Pattern)
  
  Параметры:
    #Данные - начальные данные для поиска
  
  Возвращает: найденный элемент через глобальную переменную ЭлементRet
  
  Алгоритм:
    1. Создаем стек задач с начальными данными
    2. Пока стек не пуст и результат не найден:
       a. Берем задачу из стека
       b. Обрабатываем задачу
       c. Если нужно продолжить поиск, добавляем новые задачи в стек
    3. Результат сохраняется в глобальной переменной ЭлементRet"
  
  (?catch "i: 448 Poisk-Итеративный Project-4.lsp " '; -L448
    (progn ; -L449
      ; Инициализация
      (setq #Стек-Задач (list #Данные)
            ЭлементRet nil              ; Результат еще не найден
            Список-Данных nil           ; Инициализация списка данных
            Список-Правил nil           ; Инициализация списка правил
      ) ;end setq L455
      
      ; Основной цикл обработки
      (while (and #Стек-Задач (NULL ЭлементRet)) ; -L458
        (progn ; -L459
          ; Извлечение текущей задачи из стека (LIFO - Last In First Out)
          (setq #Текущие-Данные (car #Стек-Задач)
                #Стек-Задач (cdr #Стек-Задач)
          ) ;end setq L463
          
          ; Обработка текущей задачи
          (if (and (NULL ЭлементRet) (= (type #Текущие-Данные) 'LIST)) ; -L466
            (progn ; -L467
              (setq #Атом (car #Текущие-Данные)
                    #Тип-Элемента (type #Атом)
              ) ;end setq L470
              
              (cond ; -L472
                ; СЛУЧАЙ 1: Обработка символа
                ((= #Тип-Элемента 'SYM) ; -L474
                  (progn ; -L475
                    ; Добавляем данные в список
                    (setq Список-Данных (cons #Текущие-Данные Список-Данных))
                    
                    (cond ; -L479
                      ; Найден искомый элемент
                      ((= #Атом Элемент) ; -L481
                       (setq ЭлементRet #Текущие-Данные)
                      ) ;end cond case L483
                      
                      ; Обработка классов (добавление в список правил)
                      ((and (NOT (atom (cadr #Текущие-Данные))) ; -L486
                            (setq Список-Правил
                              (if (and (NULL (assoc #Атом Список-Правил)) ; -L488
                                       (assoc #Атом *Общий-Список-Классов*)) ; -L489
                                (cons (list #Атом) Список-Правил)
                                Список-Правил
                              ) ;end and L493
                            ) ;end setq L494
                       ) ;end and L495
                       ; Не добавляем новых задач, просто обновляем список правил
                       nil
                      ) ;end cond case L498
                      
                      ; Продолжение поиска в хвосте списка
                      ((NOT (atom (setq #Атом (cdr #Текущие-Данные)))) ; -L501
                       ; ВМЕСТО РЕКУРСИИ: добавляем новую задачу в стек
                       (setq #Стек-Задач (cons #Атом #Стек-Задач))
                      ) ;end cond case L504
                    ) ;end cond L505
                  ) ;end progn L475
                ) ;end cond case L507
                
                ; СЛУЧАЙ 2: Обработка списка
                ((= #Тип-Элемента 'LIST) ; -L510
                  ; ВМЕСТО mapcar: добавляем все элементы списка в стек
                  ; Обрабатываем в обратном порядке, чтобы сохранить логику обхода
                  (foreach Элемент (reverse #Текущие-Данные)
                    (if (= (type Элемент) 'LIST) ; -L515
                      (setq #Стек-Задач (cons Элемент #Стек-Задач))
                    ) ;end if L517
                  ) ;end foreach L518
                ) ;end cond case L519
              ) ;end cond L520
            ) ;end progn L467
          ) ;end if L466
        ) ;end progn L459
      ) ;end while L458
      
      ; Результат уже в ЭлементRet
      nil
    ) ;end progn L449
  ) ;end ?catch L448
) ;end defun Poisk-Итеративный L447
(?log "L: 659 Project-4.lsp Poisk-Итеративный Potok-Итеративный ")

(defun Potok-Итеративный (#Данные / ; -L521
                          #Стек-Задач          ; Стек задач
                          #Текущие-Данные      ; Текущие данные
                          #Атом                ; Текущий атом
                          #Тип-Элемента        ; Тип элемента
                         )
  "Итеративный поиск атрибута в потоке данных (Trampoline Pattern)
  
  Параметры:
    #Данные - начальные данные для поиска
    Элемент - глобальная переменная с искомым элементом
  
  Возвращает: найденный элемент через глобальную переменную ЭлементRet"
  
  (?catch "i: 522 Potok-Итеративный Project-4.lsp " '; -L522
    (progn ; -L523
      ; Инициализация
      (setq #Стек-Задач (list #Данные)
            ЭлементRet nil
      ) ;end setq L526
      
      ; Основной цикл
      (while (and #Стек-Задач (NULL ЭлементRet)) ; -L529
        (progn ; -L530
          ; Извлечение задачи
          (setq #Текущие-Данные (car #Стек-Задач)
                #Стек-Задач (cdr #Стек-Задач)
          ) ;end setq L534
          
          ; Обработка
          (if (and (NULL ЭлементRet) (= (type #Текущие-Данные) 'LIST)) ; -L537
            (progn ; -L538
              (setq #Атом (car #Текущие-Данные)
                    #Тип-Элемента (type #Атом)
              ) ;end setq L541
              
              (cond ; -L543
                ; Найден искомый элемент
                ((AND (/= #Тип-Элемента 'LIST) (= #Атом Элемент)) ; -L545
                 (setq ЭлементRet #Текущие-Данные)
                ) ;end cond case L547
                
                ; Продолжение поиска в списке
                ((= (type #Текущие-Данные) 'LIST) ; -L550
                 ; ВМЕСТО mapcar: добавляем все элементы в стек
                 (foreach Элемент (reverse #Текущие-Данные)
                   (if (= (type Элемент) 'LIST) ; -L554
                     (setq #Стек-Задач (cons Элемент #Стек-Задач))
                   ) ;end if L556
                 ) ;end foreach L557
                ) ;end cond case L558
              ) ;end cond L559
            ) ;end progn L538
          ) ;end if L537
        ) ;end progn L530
      ) ;end while L529
      
      ; Результат уже в ЭлементRet
      nil
    ) ;end progn L523
  ) ;end ?catch L522
) ;end defun Potok-Итеративный L521
(?log "L: 739 Project-4.lsp Potok-Итеративный >> ")

;===========================================================================
; РАБОТА С ПОТОКОМ ДАННЫХ
;===========================================================================

(defun >> (Данные Элемент / ЭлементRet) ; -L633
  "Чтение атрибута из объекта
  
  Параметры:
    Данные - объект данных
    Элемент - имя атрибута
  
  Возвращает: значение атрибута"
  (?catch "i: 634 >> Project-4.lsp " '; -L634
    (progn ; -L635
      (if *Использовать-Trampoline* ; -L636
        (progn ; -L637
          (Potok-Итеративный Данные)
          (if ЭлементRet ; -L640
            (cadr ЭлементRet)
            nil
          ) ;end if L643
        ) ;end progn L637
        (progn ; -L645
          (Potok Данные)
          (if ЭлементRet ; -L648
            (cadr ЭлементRet)
            nil
          ) ;end if L651
        ) ;end progn L645
      ) ;end if L636
    ) ;end progn L635
  ) ;end ?catch L634
) ;end defun >> L633
(?log "L: 780 Project-4.lsp >> << ")

(defun << (#Список #Аттрибут #Значение / #Старый-Аттрибут) ; -L670
  "Запись атрибута в поток
  
  Параметры:
    #Список - список для записи
    #Аттрибут - имя атрибута
    #Значение - значение атрибута
  
  Возвращает: обновленный список"
  (?catch "i: 671 << Project-4.lsp " '; -L671
    (progn ; -L672
      (if (NULL (setq #Старый-Аттрибут (ASSOC #Аттрибут #Список))) ; -L674
        (if (NULL #Список) ; -L675
          (setq #Список (list (list #Аттрибут #Значение)))
          (setq #Список (cons (list #Аттрибут #Значение) #Список))
        ) ;end if L678
        (setq #Список (subst (list #Аттрибут #Значение) #Старый-Аттрибут #Список))
      ) ;end if L680
      #Список
    ) ;end progn L672
  ) ;end ?catch L671
) ;end defun << L670
(?log "L: 804 Project-4.lsp << Potok ")

(defun Potok (#Данные / #Атом #Тип-Элемента) ; -L672
  "Поиск атрибута в потоке данных
  
  Поддерживает переключение между рекурсивной и итеративной версиями
  через флаг *Использовать-Trampoline*"
  (?catch "i: 673 Potok Project-4.lsp " '; -L673
    (progn ; -L674
      (if *Использовать-Trampoline* ; -L675
        (Potok-Итеративный #Данные)
        (progn ; -L677
          ; Оригинальная рекурсивная версия
          (if (and (NULL ЭлементRet) (= (type #Данные) 'LIST)) ; -L680
            (progn ; -L681
              (setq #Атом (car #Данные)
                    #Тип-Элемента (type #Атом)
              ) ;end setq L684
              (cond ; -L686
                ((AND (/= #Тип-Элемента 'LIST) (= #Атом Элемент)) ; -L688
                 (setq ЭлементRet #Данные)
                ) ;end cond case L690
                ((= (type #Данные) 'LIST) ; -L692
                 (mapcar 'Potok #Данные)
                ) ;end cond case L694
              ) ;end cond L695
            ) ;end progn L681
          ) ;end if L680
        ) ;end progn L677
      ) ;end if L675
    ) ;end progn L674
  ) ;end ?catch L673
) ;end defun Potok L672
(?log "L: 845 Project-4.lsp Potok Poisk ")

(defun Poisk (#Данные / #Атом #Тип-Элемента) ; -L847
  "Поиск правила или атрибута в данных
  
  Поддерживает переключение между рекурсивной и итеративной версиями
  через флаг *Использовать-Trampoline*"
  (?catch "i: 852 if Project-4.lsp " '; -L852
    (if *Использовать-Trampoline* ; -L853
      (Poisk-Итеративный #Данные)
      (?catch "i: 855 progn Project-4.lsp " '; -L855
        (progn ; -L856
          ; Оригинальная рекурсивная версия
          (?catch "i: 858 if Project-4.lsp " '; -L858
            (if (and (NULL ЭлементRet) (= (type #Данные) 'LIST)) ; -L859
              (?catch "i: 860 progn Project-4.lsp " '; -L860
                (progn ; -L861
                  (?catch "i: 862 setq Project-4.lsp " '; -L862
                    (setq #Атом (car #Данные)
                          #Тип-Элемента (type #Атом)
                    )
                  )
                  (?catch "i: 867 cond Project-4.lsp " '; -L867
                    (cond ; -L868
                      ((= #Тип-Элемента 'SYM) ; -L869
                        (setq Список-Данных (cons #Данные Список-Данных))
                        (?catch "i: 871 cond Project-4.lsp " '; -L871
                          (cond ; -L872
                            ((= #Атом Элемент) ; -L873
                             (setq ЭлементRet #Данные)
                            ) ;end cond case L875
                            ((and (NOT (atom (cadr #Данные))) ; -L876
                                  (?catch "i: 877 if Project-4.lsp " '; -L877
                                    (setq Список-Правил
                                      (if (and (NULL (assoc #Атом Список-Правил)) ; -L879
                                               (assoc #Атом *Общий-Список-Классов*)) ; -L880
                                        (cons (list #Атом) Список-Правил)
                                        Список-Правил
                                      ) ;end and L883
                                    )
                                  ) ;end ?catch L885
                             ) ;end and L886
                             nil
                            ) ;end cond case L888
                            ((NOT (atom (setq #Атом (cdr #Данные)))) ; -L889
                             (Poisk #Атом)
                            ) ;end cond case L891
                          ) ;end cond L892
                        ) ;end ?catch L893
                      ) ;end cond case L894
                      ((= #Тип-Элемента 'LIST) ; -L895
                        (mapcar 'Poisk #Данные)
                      ) ;end cond case L897
                    ) ;end cond L898
                  ) ;end ?catch L899
                ) ;end progn L900
              ) ;end ?catch L901
            ) ;end if L902
          ) ;end ?catch L903
        ) ;end progn L904
      ) ;end ?catch L905
    ) ;end if L906
  ) ;end ?catch L907
) ;end defun Poisk L908
(?log "L: 909 Project-4.lsp Poisk Найти-Правило ")

;===========================================================================
; РАБОТА С ПРАВИЛАМИ
;===========================================================================
;
; ПРИМЕЧАНИЕ: Для отслеживания номера строки при выполнении системных функций
; (if, setq, progn, while, cond и т.д.) рекомендуется использовать обертку ?catch
; из Project-4-debug.lsp:
;
;   (?catch "i: 919 if Project-4.lsp "
;     (if (> A 10) 1 0)
;   )
;
; Это позволяет автоматически привязывать ошибки к номерам строк кода.
; Функция ?catch устанавливает *log-code-line* для обработчика ошибок.

(defun Найти-Правило (##Имя-Правила Список-Правил / ##Ret ##Правило ##Класс ##Список) ; -L926
  "Поиск правила в списке классов"
  (?catch "i: 928 foreach Project-4.lsp " '; -L928
    (foreach ##Класс Список-Правил
      (?catch "i: 930 if Project-4.lsp " '; -L930
        (if (NULL ##Ret) ; -L931
          (?catch "i: 932 if Project-4.lsp " '; -L932
            (if (setq ##Список (assoc (car ##Класс) *Список-Порядка-Наследования*)) ; -L933
              (?catch "i: 934 foreach Project-4.lsp " '; -L934
                (foreach ##Правило ##Список
                  (?catch "i: 936 if Project-4.lsp " '; -L936
                    (if (NULL ##Ret) ; -L937
                      (setq ##Ret (Выполнить_Правило Элемент (eval ##Правило)))
                    ) ;end if L939
                  ) ;end ?catch L940
                ) ;end foreach L941
              ) ;end ?catch L942
              (setq ##Ret (Выполнить_Правило Элемент (eval (car ##Класс))))
            ) ;end if L944
          ) ;end ?catch L945
        ) ;end if L946
      ) ;end ?catch L947
    ) ;end foreach L948
  ) ;end ?catch L949
  ##Ret
) ;end defun Найти-Правило L951
(?log "L: 952 Project-4.lsp Найти-Правило Выполнить_Правило ")

(defun Выполнить_Правило (###Элемент ###Список-Правил / ###Условие ###Ret ###Правило ###Функция ###Данные) ; -L954
  "Выполнение правила с проверкой условий"
  
  ; Установка глобальной переменной для использования в Call_Правило
  (setq *Текущий-Элемент-Правила* ###Элемент)
  
  ; Поиск в динамическом списке данных
  (?catch "i: 961 if Project-4.lsp " '; -L961
    (if (not (NULL (setq ###Данные (assoc 'Динамический-Список-Данных ###Список-Правил)))) ; -L962
      (setq ###RET (>> (eval (cadr ###Данные)) ###Элемент))
    ) ;end if L964
  ) ;end ?catch L965
  
  (?catch "i: 967 while Project-4.lsp " '; -L967
    (while (and (NULL ###Ret) (setq ###Правило (assoc ###Элемент ###Список-Правил))) ; -L968
      (?catch "i: 969 progn Project-4.lsp " '; -L969
        (progn ; -L970
          (Print-IGraf ###Правило 0)
          (?catch "i: 972 setq Project-4.lsp " '; -L972
            (setq ###Условие (cddr (car (cadr ###Правило)))
                  ###Функция (cddr (cadr (cadr ###Правило)))
            )
          )
          (?catch "i: 977 cond Project-4.lsp " '; -L977
            (cond ; -L978
              ((NULL ###Правило) ; -L979
                (setq ###Ret nil)
              ) ;end cond case L981
              ((NULL (Call_Правило ###Условие nil)) ; -L982
                (Print-IGraf ###Правило 1)
              ) ;end cond case L984
              ((progn ; -L985
                 (Print-IGraf ###Правило 2)
                 (setq ###Ret (Call_Правило ###Функция 1))
               ) ;end progn L988
              ) ;end cond case L989
            ) ;end cond L990
          ) ;end ?catch L991
        ) ;end progn L992
      ) ;end ?catch L993
      ; Замена отработанного правила
      (setq ###Список-Правил (subst '(nil) ###Правило ###Список-Правил))
    ) ;end while L996
  ) ;end ?catch L997
  
  ; Проверка на прозрачную команду
  (?catch "i: 1000 if Project-4.lsp " '; -L1000
    (if (assoc (car ###Правило) *Список-Прозрачных-Команд*) ; -L1001
      (setq ###Ret nil)
    ) ;end if L1003
  ) ;end ?catch L1004
  
  ###Ret
) ;end defun Выполнить_Правило L1007
(?log "L: 1008 Project-4.lsp Выполнить_Правило Call_Правило ")

(defun Call_Правило (####Правило ####RetMode / ####Вызов ####Условие ####Переменная ####Ret ####Separ ####Параметр ####Результат ####Bad ####Функция-Имя ####Список-Параметров ####Внешняя-Функция ####Список-Параметров-Правила ####Элемент-Результат) ; -L1010
  "Вызов правила с обработкой параметров и поддержкой внешних функций
  
  Поддерживает:
    - Поиск параметров через систему правил (#Subr=>)
    - Вызов внешних LISP функций напрямую
    - Обработку вызовов функций с параметрами, которые тоже ищутся через систему правил
    - Отладку всех вызовов"
  
  ; Получение текущего элемента правила из глобальной переменной
  (?catch "i: 1020 if Project-4.lsp " '; -L1020
    (setq ###Элемент (if (boundp '*Текущий-Элемент-Правила*)
                         *Текущий-Элемент-Правила*
                         nil))
  )
  
  ; Если правило - это просто символ функции
  (?catch "i: 1027 if Project-4.lsp " '; -L1027
    (if (and (= (type ####Правило) 'SYM) ; -L1028
             (Проверить-Внешнюю-Функцию ####Правило)) ; -L1029
      (?catch "i: 1030 progn Project-4.lsp " '; -L1030
        (progn ; -L1031
          (?catch "i: 1032 if Project-4.lsp " '; -L1032
            (if *isDebug* ; -L1033
              (?princ (strcat "\n[DEBUG] Прямой вызов внешней функции: " (vl-symbol-name ####Правило)))
            ) ;end if L1035
          ) ;end ?catch L1036
          (?catch "i: 1037 setq Project-4.lsp " '; -L1037
            (setq ####Ret
              (?catch "i: 1039 if Project-4.lsp " '; -L1039
                (if ####RetMode ; -L1040
                  (?catch "i: 1041 if Project-4.lsp " '; -L1041
                    (if ###Элемент ; -L1042
                      (list ###Элемент (####Правило))
                      (list (####Правило))
                    ) ;end if L1045
                  ) ;end ?catch L1046
                  (####Правило)
                ) ;end if L1048
              ) ;end ?catch L1049
            )
          ) ;end ?catch L1051
          ####Ret
        ) ;end progn L1053
      ) ;end ?catch L1054
    ) ;end if L1055
  ) ;end ?catch L1056
  
  ; Обычная обработка правила
  ; Инициализация вызова зависит от формата правила
  (?catch "i: 1060 cond Project-4.lsp " '; -L1060
    (cond ; -L1061
      ; Если правило начинается с defun - строим вызов функции
      ((and (= (type ####Правило) 'LIST) ; -L1063
            (= (car ####Правило) 'defun)
            (>= (length ####Правило) 2)) ; -L1065
        (setq ####Вызов (list (cadr ####Правило)))
      ) ;end and L1067
      ; Если правило - список вызова функции
      ((and (= (type ####Правило) 'LIST) (car ####Правило)) ; -L1069
        (setq ####Вызов (list (car ####Правило)))
      ) ;end and L1071
      ; Если правило - символ
      ((= (type ####Правило) 'SYM) ; -L1073
        (setq ####Вызов (list ####Правило))
      ) ;end cond case L1075
      ; По умолчанию
      (T ; -L1077
        (setq ####Вызов '(####Правило))
      ) ;end cond case L1079
    ) ;end cond L1080
  ) ;end ?catch L1081
  
  (?catch "i: 1083 setq Project-4.lsp " '; -L1083
    (setq ####Условие 1
          ####Separ 1
          ####Список-Параметров nil
          ####Внешняя-Функция nil
    )
  )
  
  ; Определение имени функции в зависимости от формата правила
  (?catch "i: 1092 cond Project-4.lsp " '; -L1092
    (cond
      ; Если правило начинается с defun - извлекаем имя функции из второго элемента
      ((and (= (type ####Правило) 'LIST) ; -L1095
            (= (car ####Правило) 'defun)
            (>= (length ####Правило) 2))
        (setq ####Функция-Имя (cadr ####Правило))
        ; Проверка, является ли это внешней функцией
        (?catch "i: 1100 if Project-4.lsp " '; -L1100
          (if (and ####Функция-Имя (Проверить-Внешнюю-Функцию ####Функция-Имя)) ; -L1101
            (setq ####Внешняя-Функция T)
          ) ;end if L1103
        ) ;end ?catch L1104
      ) ;end cond case L1105
      ; Если правило - список вызова функции
      ((and (= (type ####Правило) 'LIST) (car ####Правило)) ; -L1107
        (setq ####Функция-Имя (car ####Правило))
        ; Проверка, является ли это внешней функцией
        (?catch "i: 1110 if Project-4.lsp " '; -L1110
          (if (Проверить-Внешнюю-Функцию ####Функция-Имя) ; -L1111
            (setq ####Внешняя-Функция T)
          ) ;end if L1113
        ) ;end ?catch L1114
      ) ;end cond case L1115
      ; Если правило - символ
      ((= (type ####Правило) 'SYM) ; -L1117
        (setq ####Функция-Имя ####Правило)
        (?catch "i: 1119 if Project-4.lsp " '; -L1119
          (if (Проверить-Внешнюю-Функцию ####Функция-Имя) ; -L1120
            (setq ####Внешняя-Функция T)
          ) ;end if L1122
        ) ;end ?catch L1123
      ) ;end cond case L1124
      (T ; -L1125
        (setq ####Функция-Имя nil)
      ) ;end cond case L1127
    )
  )
  
  ; Обработка параметров правила
  ; Определяем список параметров в зависимости от формата правила
  (setq ####Список-Параметров-Правила nil)
  (?catch "i: 1134 cond Project-4.lsp " '; -L1134
    (cond ; -L1135
      ; Если правило начинается с defun - извлекаем параметры из третьего элемента
      ((and (= (type ####Правило) 'LIST) ; -L1137
            (= (car ####Правило) 'defun)
            (>= (length ####Правило) 3)) ; -L1139
        ; В defun структура: (defun имя-функции (параметры) тело)
        ; Параметры находятся в третьем элементе (caddr)
        (?catch "i: 1142 setq Project-4.lsp " '; -L1142
          (setq ####Список-Параметров-Правила
                (?catch "i: 1144 cond Project-4.lsp " '; -L1144
                  (cond ; -L1145
                    ; Если параметры - список
                    ((and (caddr ####Правило) ; -L1147
                          (listp (caddr ####Правило))) ; -L1148
                      (caddr ####Правило)
                    ) ;end and L1150
                    ; Если параметры - nil, преобразуем в пустой список
                    ((NULL (caddr ####Правило)) ; -L1152
                      nil  ; Пустой список параметров
                    ) ;end cond case L1154
                    ; Если параметры - атом, создаем список с одним элементом
                    ((caddr ####Правило) ; -L1156
                      (list (caddr ####Правило))
                    ) ;end cond case L1158
                    ; По умолчанию - пустой список
                    (T ; -L1160
                      nil
                    ) ;end cond case L1162
                  ) ;end cond L1163
                ) ;end ?catch L1164
          )
        ) ;end ?catch L1166
      ) ;end and L1167
      ; Если правило - список вызова функции (имя параметр1 параметр2 ...)
      ((and (= (type ####Правило) 'LIST) ; -L1169
            (not (member (car ####Правило) '(defun quote)))
            (car ####Правило)) ; -L1171
        (setq ####Список-Параметров-Правила (cdr ####Правило))
      ) ;end and L1173
      ; Если правило - символ или другой тип
      (T ; -L1175
        (setq ####Список-Параметров-Правила nil)
      ) ;end cond case L1177
    ) ;end cond L1178
  ) ;end ?catch L1179
  
  ; Обработка параметров
  (?catch "i: 1182 if Project-4.lsp " '; -L1182
    (if ####Список-Параметров-Правила ; -L1183
      (?catch "i: 1184 foreach Project-4.lsp " '; -L1184
        (foreach ####Переменная ####Список-Параметров-Правила
          (?catch "i: 1186 cond Project-4.lsp " '; -L1186
            (cond ; -L1187
              ((NULL ####Условие) ; -L1188
                ()
              ) ;end cond case L1190
              ((OR (NULL ####Separ) (= ####Переменная '/)) ; -L1191
                (setq ####Separ nil)
              ) ;end cond case L1193
              (T ; -L1194
                ; Поиск параметра через систему правил
                (setq ####Результат (#Subr=> ####Переменная nil))
                
                (?catch "i: 1198 if Project-4.lsp " '; -L1198
                  (if ####Результат ; -L1199
                    (?catch "i: 1200 progn Project-4.lsp " '; -L1200
                      (progn ; -L1201
                        ; Параметр найден через систему правил
                        (setq ####Параметр (cadr ####Результат))
                        (?catch "i: 1204 setq Project-4.lsp " '; -L1204
                          (setq ####Вызов
                            (cons
                              (?catch "i: 1207 cond Project-4.lsp " '; -L1207
                                (cond ; -L1208
                                  ; Если параметр - это lambda или function, не оборачиваем в QUOTE
                                  ((and (listp ####Параметр) ; -L1210
                                        (member (car ####Параметр) '(lambda function))) ; -L1211
                                    ####Параметр
                                  ) ;end and L1213
                                  ; Если параметр - это функция (USUBR/SUBR), не оборачиваем в QUOTE
                                  ((or (= (type ####Параметр) 'USUBR) ; -L1215
                                       (= (type ####Параметр) 'SUBR)) ; -L1216
                                    ####Параметр
                                  ) ;end or L1218
                                  ; Для списков оборачиваем в QUOTE
                                  ((listp ####Параметр) ; -L1220
                                    (list 'QUOTE ####Параметр)
                                  ) ;end cond case L1222
                                  ; Для остальных - как есть
                                  (T ; -L1224
                                    ####Параметр
                                  ) ;end cond case L1226
                                ) ;end cond L1227
                              ) ;end ?catch L1228
                              ####Вызов
                            )
                          )
                        ) ;end ?catch L1232
                        ; Сохраняем параметр для возможного прямого вызова
                        (setq ####Список-Параметров (cons ####Параметр ####Список-Параметров))
                      ) ;end progn L1235
                    ) ;end ?catch L1236
                    (?catch "i: 1237 progn Project-4.lsp " '; -L1237
                      (progn ; -L1238
                        ; Параметр не найден через систему правил
                        (?catch "i: 1240 if Project-4.lsp " '; -L1240
                          (if ####Внешняя-Функция ; -L1241
                            (?catch "i: 1242 progn Project-4.lsp " '; -L1242
                              (progn ; -L1243
                                ; Для внешней функции параметр может быть любым
                                (setq ####Список-Параметров (cons ####Переменная ####Список-Параметров))
                                (setq ####Вызов (cons ####Переменная ####Вызов))
                              ) ;end progn L1247
                            ) ;end ?catch L1248
                            (?catch "i: 1249 progn Project-4.lsp " '; -L1249
                              (progn ; -L1250
                                ; Для правила - ошибка, параметр не найден
                                (setq ####Условие nil)
                                (setq ####Bad ####Переменная)
                              ) ;end progn L1254
                            ) ;end ?catch L1255
                          ) ;end if L1256
                        ) ;end ?catch L1257
                      ) ;end progn L1258
                    ) ;end ?catch L1259
                  ) ;end if L1260
                ) ;end ?catch L1261
              ) ;end cond case L1262
            ) ;end cond L1263
          ) ;end ?catch L1264
        ) ;end foreach L1265
      ) ;end ?catch L1266
    ) ;end if L1267
  ) ;end ?catch L1268
  
  (?catch "i: 1270 cond Project-4.lsp " '; -L1270
    (cond ; -L1271
      ((and (NULL ####Условие) (not ####Внешняя-Функция)) ; -L1272
        (?catch "i: 1273 if Project-4.lsp " '; -L1273
          (if *isDebug* ; -L1274
            (?catch "i: 1275 progn Project-4.lsp " '; -L1275
              (progn ; -L1276
                (?princ "\nНехватает параметров для правила")
                (?princ ####Bad)
              ) ;end progn L1279
            ) ;end ?catch L1280
          ) ;end if L1281
        ) ;end ?catch L1282
        (setq ####Ret nil)
      ) ;end and L1284
      ((and ####Функция-Имя ####Внешняя-Функция) ; -L1285
        ; Вызов внешней функции напрямую с параметрами
        (if *isDebug* ; -L1287
          (?princ (strcat "\n[DEBUG] Вызов внешней функции " (vl-symbol-name ####Функция-Имя) " с параметрами через систему правил"))
        ) ;end if L1289
        (?catch "i: 1290 setq Project-4.lsp " '; -L1290
          (setq ####Ret
            (?catch "i: 1292 if Project-4.lsp " '; -L1292
              (if ####RetMode ; -L1293
                (?catch "i: 1294 if Project-4.lsp " '; -L1294
                  (if ###Элемент ; -L1295
                    (list ###Элемент (Разрешить-Вызов-Функции ####Функция-Имя (reverse ####Список-Параметров)))
                    (list (Разрешить-Вызов-Функции ####Функция-Имя (reverse ####Список-Параметров)))
                  ) ;end if L1298
                ) ;end ?catch L1299
                (Разрешить-Вызов-Функции ####Функция-Имя (reverse ####Список-Параметров))
              ) ;end if L1301
            ) ;end ?catch L1302
          )
        ) ;end ?catch L1304
      ) ;end and L1305
      (####RetMode ; -L1306
        ; Обычный вызов через eval (система правил)
        (?catch "i: 1308 setq Project-4.lsp " '; -L1308
          (setq ####Ret
            (?catch "i: 1310 if Project-4.lsp " '; -L1310
              (if ###Элемент ; -L1311
                (list ###Элемент (eval (reverse ####Вызов)))
                (list (eval (reverse ####Вызов)))
              ) ;end if L1314
            ) ;end ?catch L1315
          )
        ) ;end ?catch L1317
      ) ;end cond case L1318
      (T ; -L1319
        (setq ####Ret (eval (reverse ####Вызов)))
      ) ;end cond case L1321
    ) ;end cond L1322
  ) ;end ?catch L1323
  ####Ret
) ;end defun Call_Правило L1325
(?log "L: 1326 Project-4.lsp Call_Правило Проверить-Внешнюю-Функцию ")

;===========================================================================
; ПОДДЕРЖКА ВЫЗОВА ВНЕШНИХ LISP ФУНКЦИЙ
;===========================================================================

(defun Проверить-Внешнюю-Функцию (Имя-Функции / Тип-Функции) ; -L1332
  "Проверка, является ли функция внешней LISP функцией
  
  Параметры:
    Имя-Функции - символ имени функции
  
  Возвращает: T если функция определена, nil если нет"
  (?catch "i: 1339 if Project-4.lsp " '; -L1339
    (if (and (= (type Имя-Функции) 'SYM) ; -L1340
             (boundp Имя-Функции)) ; -L1341
      (?catch "i: 1342 progn Project-4.lsp " '; -L1342
        (progn ; -L1343
          (setq Тип-Функции (type (eval Имя-Функции)))
          (or (= Тип-Функции 'SUBR)
              (= Тип-Функции 'USUBR)
              (not (NULL (member Имя-Функции (atoms-family 1))))
          ) ;end or
        ) ;end progn L1349
      ) ;end ?catch L1350
      nil
    ) ;end if L1352
  ) ;end ?catch L1353
) ;end defun Проверить-Внешнюю-Функцию L1354
(?log "L: 1355 Project-4.lsp Проверить-Внешнюю-Функцию Вызвать-Внешнюю-Функцию ")

(defun Вызвать-Внешнюю-Функцию (Имя-Функции Параметры / Результат) ; -L1357
  "Вызов внешней LISP функции с отладкой
  
  Параметры:
    Имя-Функции - символ имени функции
    Параметры - список параметров
  
  Возвращает: результат выполнения функции"
  (?catch "i: 1365 if Project-4.lsp " '; -L1365
    (if *isDebug* ; -L1366
      (?catch "i: 1367 progn Project-4.lsp " '; -L1367
        (progn ; -L1368
          (?princ (strcat "\n[DEBUG] Вызов внешней функции: " (vl-symbol-name Имя-Функции)))
          (?catch "i: 1370 if Project-4.lsp " '; -L1370
            (if Параметры ; -L1371
              (?catch "i: 1372 progn Project-4.lsp " '; -L1372
                (progn ; -L1373
                  (?princ " с параметрами: ")
                  (?princ Параметры)
                ) ;end progn L1376
              ) ;end ?catch L1377
            ) ;end if L1378
          ) ;end ?catch L1379
        ) ;end progn L1380
      ) ;end ?catch L1381
    ) ;end if L1382
  ) ;end ?catch L1383
  
  ; Вызов функции
  (?catch "i: 1386 setq Project-4.lsp " '; -L1386
    (setq Результат
      (?catch "i: 1388 if Project-4.lsp " '; -L1388
        (if Параметры ; -L1389
          (apply Имя-Функции Параметры)
          (Имя-Функции)
        ) ;end if L1392
      ) ;end ?catch L1393
    )
  ) ;end ?catch L1395
  
  (?catch "i: 1397 if Project-4.lsp " '; -L1397
    (if *isDebug* ; -L1398
      (?catch "i: 1399 progn Project-4.lsp " '; -L1399
        (progn ; -L1400
          (?princ (strcat "\n[DEBUG] Результат: "))
          (?princ Результат)
        ) ;end progn L1403
      ) ;end ?catch L1404
    ) ;end if L1405
  ) ;end ?catch L1406
  
  Результат
) ;end defun Вызвать-Внешнюю-Функцию L1409
(?log "L: 1410 Project-4.lsp Вызвать-Внешнюю-Функцию Обработать-Вызов-Функции-С-Параметрами ")

(defun Обработать-Вызов-Функции-С-Параметрами (Имя-Функции Список-Параметров / Обработанные-Параметры Параметр Результат-Поиска) ; -L1412
  "Обработка вызова функции, где параметры тоже ищутся через систему правил
  
  Параметры:
    Имя-Функции - имя функции
    Список-Параметров - список параметров (имена правил для поиска)
  
  Возвращает: результат вызова функции с обработанными параметрами
  
  Пример:
    (Обработать-Вызов-Функции-С-Параметрами 'Проверить-Условие '(Получить-Значение))
    ; Найдет правило Получить-Значение, выполнит его, и передаст результат в Проверить-Условие"
  
  (setq Обработанные-Параметры nil)
  
  ; Обработка каждого параметра
  (?catch "i: 1428 foreach Project-4.lsp " '; -L1428
    (foreach Параметр Список-Параметров
      (?catch "i: 1430 progn Project-4.lsp " '; -L1430
        (progn ; -L1431
          ; Поиск параметра через систему правил
          (setq Результат-Поиска (#Subr=> Параметр nil))
          
          (?catch "i: 1435 if Project-4.lsp " '; -L1435
            (if Результат-Поиска ; -L1436
              (?catch "i: 1437 progn Project-4.lsp " '; -L1437
                (progn ; -L1438
                  ; Параметр найден через систему правил
                  (setq Обработанные-Параметры (cons (cadr Результат-Поиска) Обработанные-Параметры))
                  (?catch "i: 1441 if Project-4.lsp " '; -L1441
                    (if *isDebug* ; -L1442
                      (?princ (strcat "\n[DEBUG] Параметр " (vl-symbol-name Параметр) " найден через систему правил"))
                    ) ;end if L1444
                  ) ;end ?catch L1445
                ) ;end progn L1446
              ) ;end ?catch L1447
              (?catch "i: 1448 progn Project-4.lsp " '; -L1448
                (progn ; -L1449
                  ; Параметр не найден - используем как есть (может быть значением)
                  (setq Обработанные-Параметры (cons Параметр Обработанные-Параметры))
                  (?catch "i: 1452 if Project-4.lsp " '; -L1452
                    (if *isDebug* ; -L1453
                      (?princ (strcat "\n[DEBUG] Параметр " (vl-symbol-name Параметр) " используется как значение"))
                    ) ;end if L1455
                  ) ;end ?catch L1456
                ) ;end progn L1457
              ) ;end ?catch L1458
            ) ;end if L1459
          ) ;end ?catch L1460
        ) ;end progn L1461
      ) ;end ?catch L1462
    ) ;end foreach L1463
  ) ;end ?catch L1464
  
  ; Вызов функции с обработанными параметрами
  (?catch "i: 1467 if Project-4.lsp " '; -L1467
    (if Обработанные-Параметры ; -L1468
      (apply Имя-Функции (reverse Обработанные-Параметры))
      (Имя-Функции)
    ) ;end if L1471
  ) ;end ?catch L1472
) ;end defun Обработать-Вызов-Функции-С-Параметрами L1473
(?log "L: 1474 Project-4.lsp Обработать-Вызов-Функции-С-Параметрами Разрешить-Вызов-Функции ")

(defun Разрешить-Вызов-Функции (Имя-Функции Параметры) ; -L1476
  "Умное разрешение вызова функции: через систему правил или напрямую
  
  Параметры:
    Имя-Функции - символ имени функции
    Параметры - список параметров
  
  Возвращает: результат выполнения"
  (?catch "i: 1484 cond Project-4.lsp " '; -L1484
    (cond ; -L1485
      ; Попытка найти через систему правил (=>)
      ((setq Результат (#Subr=> Имя-Функции Параметры)) ; -L1487
        (?catch "i: 1488 if Project-4.lsp " '; -L1488
          (if *isDebug* ; -L1489
            (?princ (strcat "\n[DEBUG] Функция найдена через систему правил: " (vl-symbol-name Имя-Функции)))
          ) ;end if L1491
        ) ;end ?catch L1492
        (cadr Результат)
      ) ;end cond case L1494
      ; Проверка внешней LISP функции
      ((Проверить-Внешнюю-Функцию Имя-Функции) ; -L1496
        (?catch "i: 1497 if Project-4.lsp " '; -L1497
          (if Параметры ; -L1498
            (Обработать-Вызов-Функции-С-Параметрами Имя-Функции Параметры)
            (Вызвать-Внешнюю-Функцию Имя-Функции nil)
          ) ;end if L1501
        ) ;end ?catch L1502
      ) ;end cond case L1503
      ; Функция не найдена
      (T ; -L1505
        (?catch "i: 1506 if Project-4.lsp " '; -L1506
          (if *isDebug* ; -L1507
            (?catch "i: 1508 progn Project-4.lsp " '; -L1508
              (progn ; -L1509
                (?princ (strcat "\n[WARNING] Функция не найдена: " (vl-symbol-name Имя-Функции)))
                (?princ "\n[WARNING] Попытка прямого вызова через eval")
              ) ;end progn L1512
            ) ;end ?catch L1513
          ) ;end if L1514
        ) ;end ?catch L1515
        ; Последняя попытка - прямой вызов
        (?catch "i: 1517 if Project-4.lsp " '; -L1517
          (if Параметры ; -L1518
            (apply Имя-Функции Параметры)
            (Имя-Функции)
          ) ;end if L1521
        ) ;end ?catch L1522
      ) ;end cond case L1523
    ) ;end cond L1524
  ) ;end ?catch L1525
) ;end defun Разрешить-Вызов-Функции L1526
(?log "L: 1527 Project-4.lsp Разрешить-Вызов-Функции Выполнить_Правило-Профессионально ")

(defun Выполнить_Правило-Профессионально (###Элемент ###Список-Правил / ; -L1529
                                          ###Условие ###Ret ###Правило ###Функция 
                                          ###Данные ###Активные-Правила ###Отсортированные)
  "Профессиональное выполнение правил с поддержкой приоритетов и стратегий
  
  Параметры:
    ###Элемент - имя правила для выполнения
    ###Список-Правил - список правил класса
  
  Возвращает: результат выполнения правила
  
  Особенности:
    - Активация всех подходящих правил
    - Сортировка по стратегии разрешения конфликтов
    - Поддержка выполнения всех правил или только первого"
  
  ; Поиск в динамическом списке данных
  (?catch "i: 1546 if Project-4.lsp " '; -L1546
    (if (not (NULL (setq ###Данные (assoc 'Динамический-Список-Данных ###Список-Правил)))) ; -L1547
      (setq ###RET (>> (eval (cadr ###Данные)) ###Элемент))
    ) ;end if L1549
  ) ;end ?catch L1550
  
  ; Сбор всех правил с проверкой условий (активация правил)
  (setq ###Активные-Правила nil)
  (?catch "i: 1554 foreach Project-4.lsp " '; -L1554
    (foreach ###Правило ###Список-Правил
      (?catch "i: 1556 if Project-4.lsp " '; -L1556
        (if (and (= (car ###Правило) ###Элемент) ; -L1557
                 (not (NULL (setq ###Условие (cddr (car (cadr ###Правило))))))) ; -L1558
          (?catch "i: 1559 progn Project-4.lsp " '; -L1559
            (progn ; -L1560
              ; Проверка условия (DATA-IFF)
              (?catch "i: 1562 if Project-4.lsp " '; -L1562
                (if (Call_Правило ###Условие nil) ; -L1563
                  (setq ###Активные-Правила (cons ###Правило ###Активные-Правила))
                ) ;end if L1565
              ) ;end ?catch L1566
            ) ;end progn L1567
          ) ;end ?catch L1568
        ) ;end and L1569
      ) ;end ?catch L1570
    ) ;end foreach L1571
  ) ;end ?catch L1572
  
  ; Если нет активных правил, возвращаем nil
  (?catch "i: 1575 if Project-4.lsp " '; -L1575
    (if (NULL ###Активные-Правила) ; -L1576
      (setq ###Ret nil)
      (?catch "i: 1578 progn Project-4.lsp " '; -L1578
        (progn ; -L1579
          ; Сортировка активных правил по стратегии
          (setq ###Отсортированные (Сортировать-Правила-По-Стратегии 
                                      ###Активные-Правила 
                                      *Стратегия-Разрешения*))
          
          ; Выполнение правил согласно стратегии
          (?catch "i: 1586 cond Project-4.lsp " '; -L1586
            (cond ; -L1587
              ((= *Стратегия-Разрешения* 'Все-Правила) ; -L1588
                ; Выполнить все активные правила
                (?catch "i: 1590 foreach Project-4.lsp " '; -L1590
                  (foreach ###Правило ###Отсортированные
                    (?catch "i: 1592 progn Project-4.lsp " '; -L1592
                      (progn ; -L1593
                        (Print-IGraf ###Правило 2)
                        (setq ###Функция (cddr (cadr (cadr ###Правило))))
                        (Call_Правило ###Функция 1)
                      ) ;end progn L1597
                    ) ;end ?catch L1598
                  ) ;end foreach L1599
                ) ;end ?catch L1600
                (setq ###Ret (list ###Элемент T))
              ) ;end cond case L1602
              (T ; -L1603
                ; Выполнить только первое правило (стандартное поведение)
                (setq ###Правило (car ###Отсортированные))
                (?catch "i: 1606 if Project-4.lsp " '; -L1606
                  (if ###Правило ; -L1607
                    (?catch "i: 1608 progn Project-4.lsp " '; -L1608
                      (progn ; -L1609
                        (Print-IGraf ###Правило 2)
                        (setq ###Функция (cddr (cadr (cadr ###Правило))))
                        (setq ###Ret (Call_Правило ###Функция 1))
                      ) ;end progn L1613
                    ) ;end ?catch L1614
                  ) ;end if L1615
                ) ;end ?catch L1616
              ) ;end cond case L1617
            ) ;end cond L1618
          ) ;end ?catch L1619
        ) ;end progn L1620
      ) ;end ?catch L1621
    ) ;end if L1622
  ) ;end ?catch L1623
  
  ###Ret
) ;end defun Выполнить_Правило-Профессионально L1626
(?log "L: 1627 Project-4.lsp Выполнить_Правило-Профессионально Установить-Салютность ")

;===========================================================================
; СИСТЕМА ПРИОРИТЕТОВ ПРАВИЛ (SALIENCE)
;===========================================================================

(defun Установить-Салютность (Имя-Правила Приоритет) ; -L1633
  "Установка явного приоритета для правила
  
  Параметры:
    Имя-Правила - символ имени правила
    Приоритет - числовой приоритет (больше = выше приоритет)
  
  Пример:
    (Установить-Салютность 'Критическое-Правило 1000)
    (Установить-Салютность 'Обычное-Правило 100)"
  (?catch "i: 1643 if Project-4.lsp " '; -L1643
    (if (assoc Имя-Правила *Салютность-Правил*) ; -L1644
      (?catch "i: 1645 setq Project-4.lsp " '; -L1645
        (setq *Салютность-Правил*
              (subst (list Имя-Правила Приоритет) 
                     (assoc Имя-Правила *Салютность-Правил*)
                     *Салютность-Правил*))
      ) ;end ?catch L1650
      (?catch "i: 1651 setq Project-4.lsp " '; -L1651
        (setq *Салютность-Правил*
              (cons (list Имя-Правила Приоритет) *Салютность-Правил*))
      ) ;end ?catch L1654
    ) ;end if L1655
  ) ;end ?catch L1656
  nil
) ;end defun Установить-Салютность L1658
(?log "L: 1659 Project-4.lsp Установить-Салютность Получить-Салютность ")

(defun Получить-Салютность (Имя-Правила) ; -L1661
  "Получение приоритета правила
  
  Параметры:
    Имя-Правила - символ имени правила
  
  Возвращает: приоритет правила или приоритет по умолчанию"
  (?catch "i: 1668 if Project-4.lsp " '; -L1668
    (if (assoc Имя-Правила *Салютность-Правил*) ; -L1669
      (cadr (assoc Имя-Правила *Салютность-Правил*))
      *Приоритет-По-Умолчанию*
    ) ;end if L1672
  ) ;end ?catch L1673
) ;end defun Получить-Салютность L1674
(?log "L: 1675 Project-4.lsp Получить-Салютность Класс-С-Приоритетом ")

(defun Класс-С-Приоритетом (Name Value Приоритет) ; -L1677
  "Определение класса с явным приоритетом для всех правил
  
  Параметры:
    Name - имя класса (символ)
    Value - список правил класса
    Приоритет - приоритет для всех правил класса
  
  Пример:
    (Класс-С-Приоритетом 'Критический-Класс '(...) *Приоритет-Высокий*)"
  (Класс Name Value)
  ; Установка приоритетов для всех правил класса
  (?catch "i: 1689 foreach Project-4.lsp " '; -L1689
    (foreach Правило Value
      (?catch "i: 1691 if Project-4.lsp " '; -L1691
        (if (and (listp Правило) (car Правило)) ; -L1692
          (Установить-Салютность (car Правило) Приоритет)
        ) ;end and L1694
      ) ;end ?catch L1695
    ) ;end foreach L1696
  ) ;end ?catch L1697
  nil
) ;end defun Класс-С-Приоритетом L1699
(?log "L: 1700 Project-4.lsp Класс-С-Приоритетом Сортировать-Правила-По-Стратегии ")

;===========================================================================
; СТРАТЕГИИ РАЗРЕШЕНИЯ КОНФЛИКТОВ (CONFLICT RESOLUTION)
;===========================================================================

(defun Сортировать-Правила-По-Стратегии (Список-Правил Стратегия) ; -L1706
  "Сортировка правил согласно стратегии разрешения конфликтов
  
  Параметры:
    Список-Правил - список правил для сортировки
    Стратегия - стратегия сортировки:
      'Порядок-Салютности - по приоритету (убывание)
      'Порядок-Времени - по времени активации (FIFO)
      'Порядок-Списка - по порядку в списке (текущая реализация)
      'Случайный - случайный порядок
      'Все-Правила - выполнить все правила
  
  Возвращает: отсортированный список правил"
  (?catch "i: 1719 cond Project-4.lsp " '; -L1719
    (cond ; -L1720
      ((= Стратегия 'Порядок-Салютности) ; -L1721
        ; Сортировка по убыванию приоритета
        (?catch "i: 1723 vl-sort Project-4.lsp " '; -L1723
          (vl-sort Список-Правил
            (function (lambda (П1 П2) ; -L1725
              (> (Получить-Салютность (car П1))
                 (Получить-Салютность (car П2)))
            )) ;end lambda L1728
          )
        ) ;end ?catch L1730
      ) ;end cond case L1731
      ((= Стратегия 'Порядок-Времени) ; -L1732
        ; FIFO - первое пришедшее правило первым выполняется
        Список-Правил  ; Уже в правильном порядке
      ) ;end cond case L1735
      ((= Стратегия 'Порядок-Списка) ; -L1736
        ; Текущая реализация - порядок в списке
        Список-Правил
      ) ;end cond case L1739
      ((= Стратегия 'Случайный) ; -L1740
        ; Перемешивание списка
        (?catch "i: 1742 vl-sort Project-4.lsp " '; -L1742
          (vl-sort Список-Правил
            (function (lambda (П1 П2) ; -L1744
              (< (random 100) (random 100))
            )) ;end lambda L1746
          )
        ) ;end ?catch L1748
      ) ;end cond case L1749
      ((= Стратегия 'Все-Правила) ; -L1750
        ; Все правила будут выполнены
        Список-Правил
      ) ;end cond case L1753
      (T ; -L1754
        ; По умолчанию - порядок списка
        Список-Правил
      ) ;end cond case L1757
    ) ;end cond L1758
  ) ;end ?catch L1759
) ;end defun Сортировать-Правила-По-Стратегии L1760
(?log "L: 1761 Project-4.lsp Сортировать-Правила-По-Стратегии Добавить-Факт ")

;===========================================================================
; РАБОЧАЯ ПАМЯТЬ (WORKING MEMORY)
;===========================================================================

(defun Добавить-Факт (Тип-Факта Данные / ID-Факта) ; -L1767
  "Добавление факта в рабочую память
  
  Параметры:
    Тип-Факта - тип факта (символ)
    Данные - данные факта (список)
  
  Возвращает: ID факта
  
  Пример:
    (Добавить-Факт 'Критическая-Ситуация '((Тип \"Авария\") (Уровень 10)))"
  (?catch "i: 1778 setq Project-4.lsp " '; -L1778
    (setq *Счетчик-Фактов* (+ *Счетчик-Фактов* 1)
          ID-Факта *Счетчик-Фактов*
    )
  )
  (?catch "i: 1783 setq Project-4.lsp " '; -L1783
    (setq *Рабочая-Память*
          (cons (list ID-Факта Тип-Факта Данные (getvar "DATE")) 
                *Рабочая-Память*))
  )
  (?catch "i: 1788 if Project-4.lsp " '; -L1788
    (if *isDebug* ; -L1789
      (?princ (strcat "\n[Рабочая-Память] Добавлен факт #" (itoa ID-Факта) ": " (vl-symbol-name Тип-Факта)))
    ) ;end if L1791
  ) ;end ?catch L1792
  ID-Факта
) ;end defun Добавить-Факт L1794
(?log "L: 1795 Project-4.lsp Добавить-Факт Удалить-Факт ")

(defun Удалить-Факт (ID-Факта) ; -L1797
  "Удаление факта из рабочей памяти
  
  Параметры:
    ID-Факта - идентификатор факта
  
  Возвращает: T если факт удален, nil если не найден"
  (?catch "i: 1804 setq Project-4.lsp " '; -L1804
    (setq *Рабочая-Память*
          (vl-remove-if (function (lambda (Факт) (= (car Факт) ID-Факта))) ; -L1806
                        *Рабочая-Память*))
  )
  (?catch "i: 1809 if Project-4.lsp " '; -L1809
    (if *isDebug* ; -L1810
      (?princ (strcat "\n[Рабочая-Память] Удален факт #" (itoa ID-Факта)))
    ) ;end if L1812
  ) ;end ?catch L1813
  T
) ;end defun Удалить-Факт L1815
(?log "L: 1816 Project-4.lsp Удалить-Факт Найти-Факты ")

(defun Найти-Факты (Тип-Факта Условие) ; -L1818
  "Поиск фактов в рабочей памяти с условием
  
  Параметры:
    Тип-Факта - тип факта для поиска
    Условие - функция проверки (lambda (Факт) ...) или nil для всех фактов типа
  
  Возвращает: список найденных фактов
  
  Пример:
    (Найти-Факты 'Критическая-Ситуация nil)
    (Найти-Факты 'Событие (function (lambda (Ф) (> (cadr (caddr Ф)) 5))))"
  (?catch "i: 1830 vl-remove-if-not Project-4.lsp " '; -L1830
    (vl-remove-if-not
      (function (lambda (Факт) ; -L1832
        (?catch "i: 1833 and Project-4.lsp " '; -L1833
          (and (= (cadr Факт) Тип-Факта) ; -L1834
               (?catch "i: 1835 if Project-4.lsp " '; -L1835
                 (if Условие ; -L1836
                   (?catch "i: 1837 progn Project-4.lsp " '; -L1837
                     (progn ; -L1838
                       ; Правильная обработка условия
                       ; Рекурсивно удаляем все QUOTE обертки
                       (setq Условие-Обработанное Условие)
                       (?catch "i: 1842 while Project-4.lsp " '; -L1842
                         (while (and (= (type Условие-Обработанное) 'LIST) ; -L1843
                                     (= (car Условие-Обработанное) 'quote)
                                     (cadr Условие-Обработанное)) ; -L1845
                           (setq Условие-Обработанное (cadr Условие-Обработанное))
                         ) ;end while L1847
                       ) ;end ?catch L1848
                       
                       ; КРИТИЧЕСКАЯ ОБРАБОТКА: если условие - это список с QUOTE элементами
                       ; Например: ((QUOTE ...) (QUOTE lambda)) или ((QUOTE ...) (QUOTE #<USUBR ...>))
                       ; Это происходит, когда Call_Правило оборачивает параметры в QUOTE
                       (?catch "i: 1853 if Project-4.lsp " '; -L1853
                         (if (and (= (type Условие-Обработанное) 'LIST) ; -L1854
                                  (> (length Условие-Обработанное) 0)) ; -L1855
                           (?catch "i: 1856 progn Project-4.lsp " '; -L1856
                             (progn ; -L1857
                               ; Ищем lambda или USUBR в любом элементе списка
                               (?catch "i: 1859 setq Project-4.lsp " '; -L1859
                                 (setq Условие-Найдено nil
                                       Индекс 0
                                 )
                               ) ;end ?catch L1863
                               (?catch "i: 1864 while Project-4.lsp " '; -L1864
                                 (while (and (< Индекс (length Условие-Обработанное)) ; -L1865
                                             (NULL Условие-Найдено)) ; -L1866
                                   (?catch "i: 1867 progn Project-4.lsp " '; -L1867
                                     (progn ; -L1868
                                       (setq Элемент (nth Индекс Условие-Обработанное))
                                       
                                       ; Если элемент обернут в QUOTE, извлекаем
                                       (?catch "i: 1872 if Project-4.lsp " '; -L1872
                                         (if (and (= (type Элемент) 'LIST) ; -L1873
                                                  (= (car Элемент) 'quote)
                                                  (cadr Элемент)) ; -L1875
                                           (setq Элемент (cadr Элемент))
                                         ) ;end and L1877
                                       ) ;end ?catch L1878
                                       
                                       ; Проверяем, является ли это тем, что нам нужно
                                       (?catch "i: 1881 if Project-4.lsp " '; -L1881
                                         (if (or (= (type Элемент) 'USUBR) ; -L1882
                                                 (= (type Элемент) 'SUBR)
                                                 (and (= (type Элемент) 'LIST) ; -L1884
                                                      (member (car Элемент) '(lambda function)))) ; -L1885
                                           (setq Условие-Найдено Элемент)
                                         ) ;end or L1887
                                       ) ;end ?catch L1888
                                       
                                       (setq Индекс (+ Индекс 1))
                                     ) ;end progn L1891
                                   ) ;end ?catch L1892
                                 ) ;end while L1893
                               ) ;end ?catch L1894
                               
                               ; Если нашли подходящее условие, используем его
                               (?catch "i: 1897 if Project-4.lsp " '; -L1897
                                 (if Условие-Найдено ; -L1898
                                   (?catch "i: 1899 progn Project-4.lsp " '; -L1899
                                     (progn ; -L1900
                                       (?catch "i: 1901 if Project-4.lsp " '; -L1901
                                         (if *isDebug* ; -L1902
                                           (?princ (strcat "\n[DEBUG Найти-Факты] Извлечено условие из QUOTE-структуры"))
                                         ) ;end if L1904
                                       ) ;end ?catch L1905
                                       (setq Условие-Обработанное Условие-Найдено)
                                     ) ;end progn L1907
                                   ) ;end ?catch L1908
                                 ) ;end if L1909
                               ) ;end ?catch L1910
                             ) ;end progn L1911
                           ) ;end ?catch L1912
                         ) ;end and L1913
                       ) ;end ?catch L1914
                       
                       (?catch "i: 1916 cond Project-4.lsp " '; -L1916
                         (cond ; -L1917
                           ; Если условие - это функция (USUBR или SUBR)
                           ((or (= (type Условие-Обработанное) 'USUBR) ; -L1919
                                (= (type Условие-Обработанное) 'SUBR)) ; -L1920
                             ; USUBR/SUBR нужно вызывать через eval, т.к. apply не работает с ними
                             ; Строим выражение: (Условие-Обработанное 'Факт)
                             (eval (list Условие-Обработанное (list 'quote Факт)))
                           ) ;end or L1924
                           ; Если условие - это список, начинающийся с lambda
                           ((and (= (type Условие-Обработанное) 'LIST) ; -L1926
                                 (= (car Условие-Обработанное) 'lambda)) ; -L1927
                             ; Для lambda используем apply
                             (apply Условие-Обработанное (list Факт))
                           ) ;end and L1930
                           ; Если условие - это список, начинающийся с function
                           ((and (= (type Условие-Обработанное) 'LIST) ; -L1932
                                 (= (car Условие-Обработанное) 'function)) ; -L1933
                             ; Извлекаем lambda из function и вызываем
                             ; function (lambda ...) -> извлекаем lambda и вызываем
                             (?catch "i: 1936 if Project-4.lsp " '; -L1936
                               (if (and (cadr Условие-Обработанное) ; -L1937
                                        (= (type (cadr Условие-Обработанное)) 'LIST)
                                        (= (car (cadr Условие-Обработанное)) 'lambda)) ; -L1939
                                 ; Используем apply вместо eval для lambda
                                 (apply (cadr Условие-Обработанное) (list Факт))
                                 ; Если не lambda, пытаемся вызвать как функцию
                                 (?catch "i: 1943 if Project-4.lsp " '; -L1943
                                   (if (or (= (type (cadr Условие-Обработанное)) 'USUBR) ; -L1944
                                           (= (type (cadr Условие-Обработанное)) 'SUBR)) ; -L1945
                                     ; USUBR/SUBR вызываем через eval
                                     (eval (list (cadr Условие-Обработанное) (list 'quote Факт)))
                                     t  ; Если не можем вызвать, пропускаем факт
                                   ) ;end or L1949
                                 ) ;end ?catch L1950
                               ) ;end and L1951
                             ) ;end ?catch L1952
                           ) ;end and L1953
                           ; Если условие - это список вызова функции (не lambda, не function)
                           ((and (= (type Условие-Обработанное) 'LIST) ; -L1955
                                 (car Условие-Обработанное)
                                 (not (member (car Условие-Обработанное) '(quote lambda function)))) ; -L1957
                             ; Пытаемся вызвать как функцию с параметрами
                             (?catch "i: 1959 if Project-4.lsp " '; -L1959
                               (if (or (= (type (car Условие-Обработанное)) 'SYM) ; -L1960
                                       (= (type (car Условие-Обработанное)) 'USUBR)
                                       (= (type (car Условие-Обработанное)) 'SUBR)) ; -L1962
                                 (apply (car Условие-Обработанное) (cons Факт (cdr Условие-Обработанное)))
                                 t
                               ) ;end or L1965
                             ) ;end ?catch L1966
                           ) ;end and L1967
                           ; Если условие - это символ функции
                           ((= (type Условие-Обработанное) 'SYM) ; -L1969
                             ; Символ функции вызываем через eval
                             (eval (list Условие-Обработанное (list 'quote Факт)))
                           ) ;end cond case L1972
                           ; По умолчанию - возвращаем t (все факты проходят проверку)
                           (T ; -L1974
                             t
                           ) ;end cond case L1976
                         ) ;end cond L1977
                       ) ;end ?catch L1978
                     ) ;end progn L1979
                   ) ;end ?catch L1980
                 ) ;end if L1981
               ) ;end ?catch L1982
             ) ;end and L1983
           ) ;end ?catch L1984
         ) ;end lambda L1985
       ) ;end function L1986
       *Рабочая-Память*
     ) ;end vl-remove-if-not L1988
   ) ;end ?catch L1989
) ;end defun Найти-Факты L1990
(?log "L: 1991 Project-4.lsp Найти-Факты Очистить-Рабочую-Память ")

(defun Очистить-Рабочую-Память () ; -L1993
  "Очистка всей рабочей памяти
  
  Возвращает: количество удаленных фактов"
  (setq Количество (length *Рабочая-Память*))
  (?catch "i: 1998 setq Project-4.lsp " '; -L1998
    (setq *Рабочая-Память* nil
          *Счетчик-Фактов* 0
    )
  )
  (?catch "i: 2003 if Project-4.lsp " '; -L2003
    (if *isDebug* ; -L2004
      (?princ (strcat "\n[Рабочая-Память] Очищено фактов: " (itoa Количество)))
    ) ;end if L2006
  ) ;end ?catch L2007
  Количество
) ;end defun Очистить-Рабочую-Память L2009
(?log "L: 2010 Project-4.lsp Очистить-Рабочую-Память Проверить-Стабилизацию ")

;===========================================================================
; ЦИКЛ ВЫВОДА (INFERENCE CYCLE)
;===========================================================================

(defun Проверить-Стабилизацию (/ Текущее-Состояние) ; -L2016
  "Проверка изменений в рабочей памяти для определения стабилизации
  
  Возвращает: T если состояние стабилизировалось, nil если есть изменения"
  (setq Текущее-Состояние (length *Рабочая-Память*))
  (?catch "i: 2021 if Project-4.lsp " '; -L2021
    (if (= Текущее-Состояние *Последнее-Состояние-Памяти*) ; -L2022
      (?catch "i: 2023 progn Project-4.lsp " '; -L2023
        (progn ; -L2024
          (?catch "i: 2025 if Project-4.lsp " '; -L2025
            (if *isDebug* ; -L2026
              (?princ "\n[Цикл-Вывода] Достигнута стабилизация")
            ) ;end if L2028
          ) ;end ?catch L2029
          T
        ) ;end progn L2031
      ) ;end ?catch L2032
      (?catch "i: 2033 progn Project-4.lsp " '; -L2033
        (progn ; -L2034
          (setq *Последнее-Состояние-Памяти* Текущее-Состояние)
          nil
        ) ;end progn L2037
      ) ;end ?catch L2038
    ) ;end if L2039
  ) ;end ?catch L2040
) ;end defun Проверить-Стабилизацию L2041
(?log "L: 2042 Project-4.lsp Проверить-Стабилизацию Выполнить-Активные-Правила ")

(defun Выполнить-Активные-Правила (/ Изменения Правило-Список) ; -L2044
  "Выполнение всех активных правил с отслеживанием изменений
  
  Возвращает: T если были изменения, nil если нет"
  (?catch "i: 2048 setq Project-4.lsp " '; -L2048
    (setq Изменения nil
          Правило-Список *Общий-Список-Классов*
    )
  )
  
  ; Здесь должна быть логика выполнения правил
  ; с отслеживанием изменений в рабочей памяти
  ; Упрощенная версия для базовой реализации
  
  (?catch "i: 2058 if Project-4.lsp " '; -L2058
    (if *isDebug* ; -L2059
      (?princ "\n[Выполнить-Активные-Правила] Выполнение правил...")
    ) ;end if L2061
  ) ;end ?catch L2062
  
  ; Проверка изменений через сравнение состояния памяти
  (setq Изменения (not (Проверить-Стабилизацию)))
  
  Изменения
) ;end defun Выполнить-Активные-Правила L2068
(?log "L: 2069 Project-4.lsp Выполнить-Активные-Правила Цикл-Вывода ")

(defun Цикл-Вывода (Макс-Итераций / Итерация Изменения) ; -L2071
  "Выполнение цикла вывода до стабилизации или достижения максимума
  
  Параметры:
    Макс-Итераций - максимальное количество итераций (по умолчанию 100)
  
  Возвращает: количество выполненных итераций
  
  Пример:
    (Цикл-Вывода 10)  ; Максимум 10 итераций"
  (?catch "i: 2081 if Project-4.lsp " '; -L2081
    (if (NULL Макс-Итераций) ; -L2082
      (setq Макс-Итераций 100)
    ) ;end if L2084
  ) ;end ?catch L2085
  
  (?catch "i: 2087 setq Project-4.lsp " '; -L2087
    (setq Итерация 0
          Изменения t
          *Последнее-Состояние-Памяти* (length *Рабочая-Память*)
    )
  ) ;end ?catch L2092
  
  (?catch "i: 2094 if Project-4.lsp " '; -L2094
    (if *isDebug* ; -L2095
      (?princ (strcat "\n[Цикл-Вывода] Начало цикла. Макс. итераций: " (itoa Макс-Итераций)))
    ) ;end if L2097
  ) ;end ?catch L2098
  
  (?catch "i: 2100 while Project-4.lsp " '; -L2100
    (while (and (< Итерация Макс-Итераций) Изменения) ; -L2101
      (?catch "i: 2102 progn Project-4.lsp " '; -L2102
        (progn ; -L2103
          (setq Итерация (+ Итерация 1))
          (?catch "i: 2105 if Project-4.lsp " '; -L2105
            (if *isDebug* ; -L2106
              (?princ (strcat "\n[Цикл-Вывода] Итерация: " (itoa Итерация)))
            ) ;end if L2108
          ) ;end ?catch L2109
          
          ; Выполнение всех активных правил
          (setq Изменения (Выполнить-Активные-Правила))
          
          ; Проверка на стабилизацию
          (?catch "i: 2115 if Project-4.lsp " '; -L2115
            (if (not Изменения) ; -L2116
              (?catch "i: 2117 progn Project-4.lsp " '; -L2117
                (progn ; -L2118
                  (?catch "i: 2119 if Project-4.lsp " '; -L2119
                    (if *isDebug* ; -L2120
                      (?princ "\n[Цикл-Вывода] Достигнута стабилизация")
                    ) ;end if L2122
                  ) ;end ?catch L2123
                ) ;end progn L2124
              ) ;end ?catch L2125
            ) ;end if L2126
          ) ;end ?catch L2127
        ) ;end progn L2128
      ) ;end ?catch L2129
    ) ;end while L2130
  ) ;end ?catch L2131
  
  (?catch "i: 2133 if Project-4.lsp " '; -L2133
    (if *isDebug* ; -L2134
      (?catch "i: 2135 progn Project-4.lsp " '; -L2135
        (progn ; -L2136
          (?princ (strcat "\n[Цикл-Вывода] Завершено. Итераций: " (itoa Итерация)))
          (?catch "i: 2138 if Project-4.lsp " '; -L2138
            (if (= Итерация Макс-Итераций) ; -L2139
              (?princ "\n[Цикл-Вывода] Достигнут максимум итераций")
            ) ;end if L2141
          ) ;end ?catch L2142
        ) ;end progn L2143
      ) ;end ?catch L2144
    ) ;end if L2145
  ) ;end ?catch L2146
  
  Итерация
) ;end defun Цикл-Вывода L2149
(?log "L: 2150 Project-4.lsp Цикл-Вывода !Добавить-Переменные ")

;===========================================================================
; РАБОТА С ПЕРЕМЕННЫМИ КОНТЕКСТА
;===========================================================================

(defun !Добавить-Переменные (!Стек_Контекста) ; -L2156
  "Добавление переменных в стек контекста"
  (?catch "i: 2158 if Project-4.lsp " '; -L2158
    (if !Стек_Контекста ; -L2159
      (?catch "i: 2160 if Project-4.lsp " '; -L2160
        (if (atom (car !Стек_Контекста)) ; -L2161
          (Установить-Переменную (car !Стек_Контекста) (cadr !Стек_Контекста))
          (?catch "i: 2163 foreach Project-4.lsp " '; -L2163
            (foreach !Переменная !Стек_Контекста
              (Установить-Переменную (car !Переменная) (cadr !Переменная))
            ) ;end foreach L2166
          ) ;end ?catch L2167
        ) ;end if L2168
      ) ;end ?catch L2169
    ) ;end if L2170
  ) ;end ?catch L2171
) ;end defun !Добавить-Переменные L2172
(?log "L: 2173 Project-4.lsp !Добавить-Переменные Установить-Переменную ")

(defun Установить-Переменную (Имя Значение / !СтекКонтекста !Переменная !Данные) ; -L2175
  "Установка переменной в контексте This"
  (?catch "i: 2177 setq Project-4.lsp " '; -L2177
    (setq !Данные (cadr This)
          !СтекКонтекста (cadr !Данные)
    )
  )
  (setq !Переменная (assoc Имя !СтекКонтекста))
  (?catch "i: 2183 if Project-4.lsp " '; -L2183
    (if !Переменная ; -L2184
      (setq This (list 'This (list (car !Данные) (subst (list Имя Значение) !Переменная !СтекКонтекста))))
      (setq This (list 'This (list (car !Данные) (cons (list Имя Значение) !СтекКонтекста))))
    ) ;end if L2187
  ) ;end ?catch L2188
) ;end defun Установить-Переменную L2189
(?log "L: 2190 Project-4.lsp Установить-Переменную Переменная-? ")

(defun Переменная-? (Имя) ; -L2192
  "Получение значения переменной из контекста"
  (cadr (assoc Имя (cadr (cadr This))))
) ;end defun Переменная-? L2195
(?log "L: 2196 Project-4.lsp Переменная-? Класс ")

;===========================================================================
; ОПРЕДЕЛЕНИЕ КЛАССОВ
;===========================================================================

(defun Класс (Name Value) ; -L2202
  "Определение класса с правилами
  
  Параметры:
    Name - имя класса (символ)
    Value - список правил класса"
  
  (set Name Value)

  ;(Setq tt (vl-catch-all-apply     (if (NULL (assoc Name *Общий-Список-Классов*)) ; -L2220
  ;    (setq *Общий-Список-Классов* (cons (list Name) *Общий-Список-Классов*))
  ;  )
  ; )
 ;)
  ; Добавление в общий список классов
  (?catch "i: 2219 if Project-4.lsp " '; -L2219
    (if (NULL (assoc Name *Общий-Список-Классов*)) ; -L2220
      (setq *Общий-Список-Классов* (cons (list Name) *Общий-Список-Классов*))
    ) ;end if L2222
  ) ;end ?catch L2223
  
  ; Сохранение структуры классов для визуализации
  (if (boundp 'Сохранить-Структуру-Классов) ; -L2225
    (Сохранить-Структуру-Классов Name) ; -L2226
  ) ;end if L2225
  
  nil
) ;end defun Класс L2226
(?log "L: 2227 Project-4.lsp Класс Порядок-Наследования: ")

(defun Порядок-Наследования: (Элемент Список-Наследования) ; -L2229
  "Установка порядка наследования для класса
  
  Параметры:
    Элемент - имя класса
    Список-Наследования - список родительских классов"
  
  (?catch "i: 2236 if Project-4.lsp " '; -L2236
     (if (NULL (assoc Элемент *Список-Порядка-Наследования*)) ; -L2237
      (?catch "i: 2238 setq Project-4.lsp " '; -L2238
        (setq *Список-Порядка-Наследования*
              (cons (cons Элемент Список-Наследования) *Список-Порядка-Наследования*)
        )
      ) ;end ?catch L2242
    ) ;end if L2243
  ) ;end ?catch L2244
) ;end defun Порядок-Наследования: L2245
(?log "L: 2246 Project-4.lsp Порядок-Наследования: =L ")

;===========================================================================
; ВСПОМОГАТЕЛЬНЫЕ ФУНКЦИИ
;===========================================================================

(defun =L (Lisp-1 Lisp-2) ; -L2277
  "Сравнение двух LISP выражений"
  (?catch "i: 2279 if Project-4.lsp " '; -L2279
    (if (assoc (list lisp-1) (list (list (list Lisp-2)))) ; -L2280
      t
      nil
    ) ;end if L2283
  ) ;end ?catch L2284
) ;end defun =L L2285
(?log "L: 2286 Project-4.lsp =L Включить-Trampoline ")

;===========================================================================
; УПРАВЛЕНИЕ TRAMPOLINE PATTERN
;===========================================================================

(defun Включить-Trampoline ()
  "Включение Trampoline Pattern для преобразования рекурсии в итерацию"
  (setq *Использовать-Trampoline* t)
  (?princ "\n[Trampoline] Включен - используется итеративный подход")
  (?princ)
)
(?log "L: 2427 Project-4.lsp Включить-Trampoline Выключить-Trampoline ")

(defun Выключить-Trampoline ()
  "Выключение Trampoline Pattern - возврат к рекурсивному подходу"
  (setq *Использовать-Trampoline* nil)
  (?princ "\n[Trampoline] Выключен - используется рекурсивный подход")
  (?princ)
)
(?log "L: 2435 Project-4.lsp Выключить-Trampoline Установить-Макс-Глубину-Рекурсии ")

(defun Установить-Макс-Глубину-Рекурсии (Глубина)
  "Установка максимальной глубины рекурсии
  
  Параметры:
    Глубина - максимальная глубина рекурсии (по умолчанию 1000)"
  (setq *Макс-Глубина-Рекурсии* Глубина)
  (?princ (strcat "\n[Настройка] Максимальная глубина рекурсии установлена: " (itoa Глубина)))
  (?princ)
)
(?log "L: 2446 Project-4.lsp Установить-Макс-Глубину-Рекурсии Очистить-Историю-Вызовов ")

(defun Очистить-Историю-Вызовов ()
  "Очистка истории вызовов для обнаружения циклов"
  (setq *История-Вызовов* nil)
  (?princ "\n[История] История вызовов очищена")
  (?princ)
)
(?log "L: 2454 Project-4.lsp Очистить-Историю-Вызовов Получить-Статус-Trampoline ")

(defun Получить-Статус-Trampoline (/ Статус Глубина История-Длина) ; -L2456
  "Получение текущего статуса Trampoline Pattern"
  (setq Статус (if (and (boundp '*Использовать-Trampoline*) *Использовать-Trampoline*) 
                   "Включен" 
                   "Выключен")
        Глубина (if (and (boundp '*Макс-Глубина-Рекурсии*)
                         *Макс-Глубина-Рекурсии* 
                         (or (= (type *Макс-Глубина-Рекурсии*) 'INT)
                             (= (type *Макс-Глубина-Рекурсии*) 'REAL)))
                    *Макс-Глубина-Рекурсии*
                    1000)
        История-Длина (if (and (boundp '*История-Вызовов*)
                               *История-Вызовов* 
                               (= (type *История-Вызовов*) 'LIST))
                          (length *История-Вызовов*)
                          0)
  ) ;end setq L2472
  (?princ (strcat "\n[Trampoline] Статус: " Статус))
  (?princ (strcat "\n[Настройки] Максимальная глубина рекурсии: " (itoa (fix Глубина))))
  (?princ (strcat "\n[История] Записей в истории вызовов: " (itoa История-Длина)))
  (?princ)
) ;end defun Получить-Статус-Trampoline L2477
(?log "L: 2478 Project-4.lsp Получить-Статус-Trampoline Создать-Continuation ")

;===========================================================================
; CONTINUATION PATTERN - Основные функции
;===========================================================================

(defun Создать-Continuation (Имя Описание / ID Состояние Время) ; -L2484
  "Создает continuation - сохраняет текущее состояние вывода
  
  Параметры:
    Имя - символьное имя continuation
    Описание - текстовое описание
  
  Возвращает: ID созданного continuation
  
  Состояние включает:
    - Рабочая память (*Рабочая-Память*)
    - Контекст This
    - Уровень рекурсии
    - Стек правил
    - Временная метка"
  
  (?catch "i: 2500 setq Project-4.lsp " '; -L2500
    (setq *Счетчик-Continuation* (+ *Счетчик-Continuation* 1)
          ID *Счетчик-Continuation*
          Время (getvar "DATE")
    )
  )
  
  ; Глубокое копирование состояния
  (?catch "i: 2508 setq Project-4.lsp " '; -L2508
    (setq Состояние (list
      (cons 'ID ID)
      (cons 'Имя Имя)
      (cons 'Описание Описание)
      (cons 'Время Время)
      (cons 'Рабочая-Память (Глубокое-Копирование *Рабочая-Память*))
      (cons 'This (if (boundp 'This) (Глубокое-Копирование This) nil))
      (cons 'Уровень-Рекурсии *Уровень-Рекурсии*)
      (cons 'Счетчик-Фактов *Счетчик-Фактов*)
    ))
  )
  
  ; Добавляем в стек
  (setq *Стек-Continuation* (cons Состояние *Стек-Continuation*))
  
  ; Ограничиваем размер стека
  (?catch "i: 2525 if Project-4.lsp " '; -L2525
    (if (> (length *Стек-Continuation*) *Максимум-Continuation*) ; -L2526
      (?catch "i: 2527 setq Project-4.lsp " '; -L2527
        (setq *Стек-Continuation*
          (reverse (cdr (reverse *Стек-Continuation*))))
      ) ;end ?catch L2530
    ) ;end if L2531
  ) ;end ?catch L2532
  
  (?catch "i: 2534 if Project-4.lsp " '; -L2534
    (if *isDebug* ; -L2535
      (?catch "i: 2536 progn Project-4.lsp " '; -L2536
        (progn ; -L2537
          (?princ (strcat "\n[Continuation] Создан #" (itoa ID) ": " (vl-symbol-name Имя)))
          ; Вызов функции отладки если доступна
          (?catch "i: 2540 if Project-4.lsp " '; -L2540
            (if (and (boundp 'Debug-Continuation-Создан) Debug-Continuation-Создан) ; -L2541
              (Debug-Continuation-Создан ID Имя Описание)
            ) ;end and L2543
          ) ;end ?catch L2544
        ) ;end progn L2545
      ) ;end ?catch L2546
    ) ;end if L2547
  ) ;end ?catch L2548
  
  ID
) ;end defun Создать-Continuation L2551
(?log "L: 2552 Project-4.lsp Создать-Continuation Глубокое-Копирование ")

(defun Глубокое-Копирование (Объект) ; -L2554
  "Выполняет глубокое копирование списка или атома
  
  Параметры:
    Объект - объект для копирования
  
  Возвращает: глубокую копию объекта"
  
  (?catch "i: 2562 cond Project-4.lsp " '; -L2562
    (cond ; -L2563
      ; Если nil, возвращаем nil
      ((NULL Объект) nil) ; -L2565
      
      ; Если атом (не список), возвращаем как есть
      ((atom Объект) Объект) ; -L2568
      
      ; Если список, рекурсивно копируем элементы
      ((= (type Объект) 'LIST) ; -L2571
        (mapcar 'Глубокое-Копирование Объект)
      ) ;end cond case L2573
      
      ; Для других типов возвращаем как есть
      (T Объект) ; -L2576
    ) ;end cond L2577
  ) ;end ?catch L2578
) ;end defun Глубокое-Копирование L2579
(?log "L: 2580 Project-4.lsp Глубокое-Копирование Восстановить-Continuation ")

(defun Восстановить-Continuation (ID / Состояние Найден) ; -L2582
  "Восстанавливает состояние из continuation
  
  Параметры:
    ID - идентификатор continuation
  
  Возвращает: T если успешно, nil если не найдено"
  
  (setq Найден nil)
  
  ; Поиск в стеке
  (?catch "i: 2593 foreach Project-4.lsp " '; -L2593
    (foreach Состояние *Стек-Continuation*
      (?catch "i: 2595 if Project-4.lsp " '; -L2595
        (if (and (NULL Найден) (= (cdr (assoc 'ID Состояние)) ID)) ; -L2596
          (?catch "i: 2597 progn Project-4.lsp " '; -L2597
            (progn ; -L2598
              ; Восстанавливаем состояние
              (?catch "i: 2600 setq Project-4.lsp " '; -L2600
                (setq *Рабочая-Память* (Глубокое-Копирование (cdr (assoc 'Рабочая-Память Состояние)))
                      This (Глубокое-Копирование (cdr (assoc 'This Состояние)))
                      *Уровень-Рекурсии* (cdr (assoc 'Уровень-Рекурсии Состояние))
                      *Счетчик-Фактов* (cdr (assoc 'Счетчик-Фактов Состояние))
                      Найден T
                )
              ) ;end ?catch L2607
              
              (?catch "i: 2609 if Project-4.lsp " '; -L2609
                (if *isDebug* ; -L2610
                  (?catch "i: 2611 progn Project-4.lsp " '; -L2611
                    (progn ; -L2612
                      (?princ (strcat "\n[Continuation] Восстановлен #" (itoa ID) ": " 
                                    (vl-symbol-name (cdr (assoc 'Имя Состояние)))))
                      ; Вызов функции отладки если доступна
                      (?catch "i: 2616 if Project-4.lsp " '; -L2616
                        (if (and (boundp 'Debug-Continuation-Восстановлен) Debug-Continuation-Восстановлен) ; -L2617
                          (Debug-Continuation-Восстановлен ID (cdr (assoc 'Имя Состояние)))
                        ) ;end and L2619
                      ) ;end ?catch L2620
                    ) ;end progn L2621
                  ) ;end ?catch L2622
                ) ;end if L2623
              ) ;end ?catch L2624
            ) ;end progn L2625
          ) ;end ?catch L2626
        ) ;end and L2627
      ) ;end ?catch L2628
    ) ;end foreach L2629
  ) ;end ?catch L2630
  
  (?catch "i: 2632 if Project-4.lsp " '; -L2632
    (if (NULL Найден) ; -L2633
      (?catch "i: 2634 if Project-4.lsp " '; -L2634
        (if *isDebug* ; -L2635
          (?princ (strcat "\n[Continuation] ОШИБКА: Не найден #" (itoa ID)))
        ) ;end if L2637
      ) ;end ?catch L2638
    ) ;end if L2639
  ) ;end ?catch L2640
  
  Найден
) ;end defun Восстановить-Continuation L2643
(?log "L: 2644 Project-4.lsp Восстановить-Continuation Найти-Continuation-По-Имени ")

(defun Найти-Continuation-По-Имени (Имя / Состояние Результат) ; -L2646
  "Находит continuation по имени
  
  Параметры:
    Имя - символьное имя continuation
  
  Возвращает: ID continuation или nil"
  
  (setq Результат nil)
  
  (?catch "i: 2656 foreach Project-4.lsp " '; -L2656
    (foreach Состояние *Стек-Continuation*
      (?catch "i: 2658 if Project-4.lsp " '; -L2658
        (if (and (NULL Результат) (= (cdr (assoc 'Имя Состояние)) Имя)) ; -L2659
          (setq Результат (cdr (assoc 'ID Состояние)))
        ) ;end and L2661
      ) ;end ?catch L2662
    ) ;end foreach L2663
  ) ;end ?catch L2664
  
  Результат
) ;end defun Найти-Continuation-По-Имени L2667
(?log "L: 2668 Project-4.lsp Найти-Continuation-По-Имени Удалить-Continuation ")

(defun Удалить-Continuation (ID / Новый-Стек) ; -L2670
  "Удаляет continuation из стека
  
  Параметры:
    ID - идентификатор continuation
  
  Возвращает: T если удален, nil если не найден"
  
  (?catch "i: 2678 setq Project-4.lsp " '; -L2678
    (setq Новый-Стек
      (?catch "i: 2680 vl-remove-if Project-4.lsp " '; -L2680
        (vl-remove-if
          (function (lambda (Состояние) ; -L2682
            (= (cdr (assoc 'ID Состояние)) ID)))
          *Стек-Continuation*
        )
      )
    )
  )
  
  (?catch "i: 2690 if Project-4.lsp " '; -L2690
    (if (/= (length Новый-Стек) (length *Стек-Continuation*)) ; -L2691
      (?catch "i: 2692 progn Project-4.lsp " '; -L2692
        (progn ; -L2693
          (setq *Стек-Continuation* Новый-Стек)
          (?catch "i: 2695 if Project-4.lsp " '; -L2695
            (if *isDebug* ; -L2696
              (?catch "i: 2697 progn Project-4.lsp " '; -L2697
                (progn ; -L2698
                  (?princ (strcat "\n[Continuation] Удален #" (itoa ID)))
                  ; Вызов функции отладки если доступна
                  (?catch "i: 2701 if Project-4.lsp " '; -L2701
                    (if (and (boundp 'Debug-Continuation-Удален) Debug-Continuation-Удален) ; -L2702
                      (Debug-Continuation-Удален ID)
                    ) ;end and L2704
                  ) ;end ?catch L2705
                ) ;end progn L2706
              ) ;end ?catch L2707
            ) ;end if L2708
          ) ;end ?catch L2709
          T
        ) ;end progn L2711
      ) ;end ?catch L2712
      (?catch "i: 2713 progn Project-4.lsp " '; -L2713
        (progn ; -L2714
          (?catch "i: 2715 if Project-4.lsp " '; -L2715
            (if *isDebug* ; -L2716
              (?princ (strcat "\n[Continuation] ОШИБКА: Не найден #" (itoa ID)))
            ) ;end if L2718
          ) ;end ?catch L2719
          nil
        ) ;end progn L2721
      ) ;end ?catch L2722
    ) ;end if L2723
  ) ;end ?catch L2724
) ;end defun Удалить-Continuation L2725
(?log "L: 2726 Project-4.lsp Удалить-Continuation Список-Continuation ")

(defun Список-Continuation (/ Состояние Список) ; -L2728
  "Возвращает список всех continuation
  
  Возвращает: список (ID Имя Описание Время)"
  
  (setq Список nil)
  
  (?catch "i: 2735 foreach Project-4.lsp " '; -L2735
    (foreach Состояние *Стек-Continuation*
      (?catch "i: 2737 setq Project-4.lsp " '; -L2737
        (setq Список (cons
          (list ; -L2739
            (cdr (assoc 'ID Состояние))
            (cdr (assoc 'Имя Состояние))
            (cdr (assoc 'Описание Состояние))
            (cdr (assoc 'Время Состояние))
          ) ;end list L2744
          Список
        ))
      )
    )
  )
  
  (reverse Список)
) ;end defun Список-Continuation L2752
(?log "L: 2753 Project-4.lsp Список-Continuation Очистить-Continuation ")

(defun Очистить-Continuation () ; -L2755
  "Очищает стек continuation"
  (?catch "i: 2757 setq Project-4.lsp " '; -L2757
    (setq *Стек-Continuation* nil
          *Счетчик-Continuation* 0
    )
  )
  (?catch "i: 2762 if Project-4.lsp " '; -L2762
    (if *isDebug* ; -L2763
      (?princ "\n[Continuation] Стек очищен")
    ) ;end if L2765
  ) ;end ?catch L2766
  nil
) ;end defun Очистить-Continuation L2768
(?log "L: 2769 Project-4.lsp Очистить-Continuation c:Сохранить-Состояние ")

;===========================================================================
; CONTINUATION PATTERN - Команды AutoCAD
;===========================================================================

(defun c:Сохранить-Состояние (/ Имя Описание ID)
  "Команда для создания continuation - сохранения текущего состояния
  
  Команда: Сохранить-Состояние"
  
  (?princ "\n+===============================================================+")
  (?princ "\n|           СОХРАНЕНИЕ СОСТОЯНИЯ ВЫВОДА                        |")
  (?princ "\n+===============================================================+")
  
  (?princ "\n\nВведите имя состояния (символ без пробелов): ")
  (setq Имя-Строка (getstring))
  
  (?catch "i: 2787 if Project-4.lsp " '; -L2787
    (if (and Имя-Строка (/= Имя-Строка "")) ; -L2788
      (?catch "i: 2789 progn Project-4.lsp " '; -L2789
        (progn ; -L2790
          (setq Имя (read Имя-Строка))
          
          (?princ "\nВведите описание (необязательно): ")
          (setq Описание (getstring T))
          
          (?catch "i: 2796 if Project-4.lsp " '; -L2796
            (if (or (null Описание) (= Описание "")) ; -L2797
              (setq Описание "Нет описания")
            ) ;end or L2799
          ) ;end ?catch L2800
          
          (setq ID (Создать-Continuation Имя Описание))
          
          (?princ "\n\n? Состояние сохранено успешно!")
          (?princ (strcat "\n  ID: " (itoa ID)))
          (?princ (strcat "\n  Имя: " (vl-symbol-name Имя)))
          (?princ (strcat "\n  Описание: " Описание))
          (?princ (strcat "\n  Всего сохранено: " (itoa (length *Стек-Continuation*))))
        ) ;end progn L2809
      ) ;end ?catch L2810
      (?princ "\n\n! Ошибка: имя не может быть пустым")
    ) ;end and L2812
  ) ;end ?catch L2813
  
  (?princ "\n")
  (?princ)
)

(defun c:Продолжи (/ Список ID-Выбор Состояние i)
  "Команда для восстановления continuation
  
  Команда: Продолжи"
  
  (?princ "\n+===============================================================+")
  (?princ "\n|           ВОССТАНОВЛЕНИЕ СОСТОЯНИЯ ВЫВОДА                    |")
  (?princ "\n+===============================================================+")
  
  (setq Список (Список-Continuation))
  
  (?catch "i: 2830 if Project-4.lsp " '; -L2830
    (if (null Список) ; -L2831
      (?catch "i: 2832 progn Project-4.lsp " '; -L2832
        (progn ; -L2833
          (?princ "\n\n! Нет сохраненных состояний")
          (?princ "\n  Используйте команду Сохранить-Состояние для создания\n")
        ) ;end progn L2836
      ) ;end ?catch L2837
      (?catch "i: 2838 progn Project-4.lsp " '; -L2838
        (progn ; -L2839
          ; Показываем список
          (?princ "\n\nДоступные сохраненные состояния:\n")
          (?princ "\n+---------------------------------------------------------------+")
          (?princ "\n| ID  | Имя                  | Описание                          |")
          (?princ "\n+---------------------------------------------------------------+")
          
          (setq i 0)
          (?catch "i: 2847 foreach Project-4.lsp " '; -L2847
            (foreach Состояние Список
              (?catch "i: 2849 progn Project-4.lsp " '; -L2849
                (progn ; -L2850
                  (?princ "\n| ")
                  (?princ (vl-string-right-trim " " (strcat (itoa (nth 0 Состояние)) "   ")))
                  (?princ " | ")
                  (setq Имя-Строка (vl-symbol-name (nth 1 Состояние)))
                  (?catch "i: 2855 if Project-4.lsp " '; -L2855
                    (if (> (strlen Имя-Строка) 20) ; -L2856
                      (setq Имя-Строка (strcat (substr Имя-Строка 1 17) "..."))
                    ) ;end if L2858
                  ) ;end ?catch L2859
                  (?princ (vl-string-right-trim " " (strcat Имя-Строка "                    ")))
                  (?princ " | ")
                  (setq Описание (nth 2 Состояние))
                  (?catch "i: 2863 if Project-4.lsp " '; -L2863
                    (if (> (strlen Описание) 33) ; -L2864
                      (setq Описание (strcat (substr Описание 1 30) "..."))
                    ) ;end if L2866
                  ) ;end ?catch L2867
                  (?princ (vl-string-right-trim " " (strcat Описание "                                 ")))
                  (?princ " |")
                  (setq i (+ i 1))
                ) ;end progn L2871
              ) ;end ?catch L2872
            ) ;end foreach L2873
          ) ;end ?catch L2874
          
          (?princ "\n+---------------------------------------------------------------+")
          
          ; Запрашиваем выбор
          (?princ "\n\nВведите ID состояния для восстановления (0 - отмена): ")
          (setq ID-Выбор (getint))
          
          (?catch "i: 2882 if Project-4.lsp " '; -L2882
            (if (and ID-Выбор (> ID-Выбор 0)) ; -L2883
              (?catch "i: 2884 progn Project-4.lsp " '; -L2884
                (progn ; -L2885
                  (?catch "i: 2886 if Project-4.lsp " '; -L2886
                    (if (Восстановить-Continuation ID-Выбор) ; -L2887
                      (?catch "i: 2888 progn Project-4.lsp " '; -L2888
                        (progn ; -L2889
                          (?princ "\n\n? Состояние восстановлено успешно!")
                          (?princ (strcat "\n  Восстановлено ID: " (itoa ID-Выбор)))
                          (?princ (strcat "\n  Фактов в памяти: " (itoa (length *Рабочая-Память*))))
                        ) ;end progn L2893
                      ) ;end ?catch L2894
                      (?princ (strcat "\n\n! Ошибка: состояние #" (itoa ID-Выбор) " не найдено"))
                    ) ;end if L2896
                  ) ;end ?catch L2897
                ) ;end progn L2898
              ) ;end ?catch L2899
            ) ;end and L2900
          ) ;end ?catch L2901
        ) ;end progn L2902
      ) ;end ?catch L2903
    ) ;end if L2904
  ) ;end ?catch L2905
  
  (?princ "\n")
  (?princ)
)
(?log "L: 2910 Project-4.lsp c:Продолжи c:Список-Continuation ")

(defun c:Список-Continuation (/ Список Состояние i)
  "Команда для просмотра списка всех continuation
  
  Команда: Список-Continuation"
  
  (?princ "\n+===============================================================+")
  (?princ "\n|           СПИСОК СОХРАНЕННЫХ СОСТОЯНИЙ                       |")
  (?princ "\n+===============================================================+")
  
  (setq Список (Список-Continuation))
  
  (?catch "i: 2923 if Project-4.lsp " '; -L2923
    (if (null Список) ; -L2924
      (?princ "\n\n! Нет сохраненных состояний\n")
      (?catch "i: 2926 progn Project-4.lsp " '; -L2926
        (progn ; -L2927
          (?princ (strcat "\n\nВсего сохранено: " (itoa (length Список)) " состояний"))
          (?princ (strcat "\nМаксимум: " (itoa *Максимум-Continuation*) " состояний\n"))
          
          (?princ "\n+---------------------------------------------------------------+")
          (?princ "\n| ID  | Имя                  | Описание                          |")
          (?princ "\n+---------------------------------------------------------------+")
          
          (setq i 0)
          (?catch "i: 2936 foreach Project-4.lsp " '; -L2936
            (foreach Состояние Список
              (?catch "i: 2938 progn Project-4.lsp " '; -L2938
                (progn ; -L2939
                  (?princ "\n| ")
                  (?princ (vl-string-right-trim " " (strcat (itoa (nth 0 Состояние)) "   ")))
                  (?princ " | ")
                  (setq Имя-Строка (vl-symbol-name (nth 1 Состояние)))
                  (?catch "i: 2944 if Project-4.lsp " '; -L2944
                    (if (> (strlen Имя-Строка) 20) ; -L2945
                      (setq Имя-Строка (strcat (substr Имя-Строка 1 17) "..."))
                    ) ;end if L2947
                  ) ;end ?catch L2948
                  (?princ (vl-string-right-trim " " (strcat Имя-Строка "                    ")))
                  (?princ " | ")
                  (setq Описание (nth 2 Состояние))
                  (?catch "i: 2952 if Project-4.lsp " '; -L2952
                    (if (> (strlen Описание) 33) ; -L2953
                      (setq Описание (strcat (substr Описание 1 30) "..."))
                    ) ;end if L2955
                  ) ;end ?catch L2956
                  (?princ (vl-string-right-trim " " (strcat Описание "                                 ")))
                  (?princ " |")
                  (setq i (+ i 1))
                ) ;end progn L2960
              ) ;end ?catch L2961
            ) ;end foreach L2962
          ) ;end ?catch L2963
        ) ;end progn L2964
      ) ;end ?catch L2965
    ) ;end if L2966
  ) ;end ?catch L2967
  
  (?princ "\n+---------------------------------------------------------------+")
  (?princ "\n\nИспользуйте команду Продолжи для восстановления состояния")
  
  (?princ "\n")
  (?princ)
)
(?log "L: 2975 Project-4.lsp c:Список-Continuation c:Очистить-Состояния ")

(defun c:Очистить-Состояния (/ Подтверждение)
  "Команда для очистки всех continuation
  
  Команда: Очистить-Состояния"
  
  (?princ "\n+===============================================================+")
  (?princ "\n|           ОЧИСТКА СОХРАНЕННЫХ СОСТОЯНИЙ                      |")
  (?princ "\n+===============================================================+")
  
  (?catch "i: 2986 if Project-4.lsp " '; -L2986
    (if (null *Стек-Continuation*) ; -L2987
      (?princ "\n\n! Нет сохраненных состояний\n")
      (?catch "i: 2989 progn Project-4.lsp " '; -L2989
        (progn ; -L2990
          (?princ (strcat "\n\nВсего сохранено: " (itoa (length *Стек-Continuation*)) " состояний"))
          (?princ "\n\nВы уверены, что хотите удалить ВСЕ сохраненные состояния?")
          (?princ "\nВведите YES для подтверждения: ")
          (setq Подтверждение (getstring))
          
          (?catch "i: 2996 if Project-4.lsp " '; -L2996
            (if (= (strcase Подтверждение) "YES") ; -L2997
              (?catch "i: 2998 progn Project-4.lsp " '; -L2998
                (progn ; -L2999
                  (Очистить-Continuation)
                  (?princ "\n\n? Все состояния удалены")
                ) ;end progn L3002
              ) ;end ?catch L3003
              (?princ "\n\n? Операция отменена")
            ) ;end if L3005
          ) ;end ?catch L3006
        ) ;end progn L3007
      ) ;end ?catch L3008
    ) ;end if L3009
  ) ;end ?catch L3010
  
  (?princ "\n")
  (?princ)
)
(?log "L: 3015 Project-4.lsp c:Очистить-Состояния Переменная? ")

;===========================================================================
; КОМАНДА УНИФИЦИРОВАННОГО ЭКСПОРТА
;===========================================================================

(defun c:Экспорт-Решения (/ Выбор Имя-Файла Тип-Данных Результат)
  "Унифицированная команда экспорта с выбором формата
  
  Команда: Экспорт-Решения"
  
  (?princ "\n+===============================================================+")
  (?princ "\n|           ЭКСПОРТ СТРУКТУРЫ РЕШЕНИЙ                           |")
  (?princ "\n+===============================================================+")
  
  ; Загрузка модулей экспорта если еще не загружены
  (?catch "i: 3031 if Project-4.lsp " '; -L3031
    (if (not (and (boundp 'Экспорт-Continuation-JSON) ; -L3032
                  (boundp 'Экспорт-Continuation-DOT)
                  (boundp 'Экспорт-Continuation-XML))) ; -L3034
      (?catch "i: 3035 progn Project-4.lsp " '; -L3035
        (progn ; -L3036
          (?princ "\n\nЗагрузка модулей экспорта...")
          (?catch "i: 3038 if Project-4.lsp " '; -L3038
            (if (findfile "Project-4-export-json.lsp") ; -L3039
              (load "Project-4-export-json.lsp")
              (?princ "\n! Предупреждение: Project-4-export-json.lsp не найден")
            ) ;end if L3042
          ) ;end ?catch L3043
          (?catch "i: 3044 if Project-4.lsp " '; -L3044
            (if (findfile "Project-4-export-dot.lsp") ; -L3045
              (load "Project-4-export-dot.lsp")
              (?princ "\n! Предупреждение: Project-4-export-dot.lsp не найден")
            ) ;end if L3048
          ) ;end ?catch L3049
          (?catch "i: 3050 if Project-4.lsp " '; -L3050
            (if (findfile "Project-4-export-xml.lsp") ; -L3051
              (load "Project-4-export-xml.lsp")
              (?princ "\n! Предупреждение: Project-4-export-xml.lsp не найден")
            ) ;end if L3054
          ) ;end ?catch L3055
        ) ;end progn L3056
      ) ;end ?catch L3057
    ) ;end and L3058
  ) ;end ?catch L3059
  
  ; Выбор типа данных для экспорта
  (?princ "\n\n+---------------------------------------------------------------+")
  (?princ "\n| ЧТО ЭКСПОРТИРОВАТЬ?                                           |")
  (?princ "\n+---------------------------------------------------------------+")
  (?princ "\n|  1 - Continuation (сохраненные состояния)                     |")
  (?princ "\n|  2 - Рабочая память (факты)                                   |")
  (?princ "\n|  3 - Полная структура системы                                 |")
  (?princ "\n|  4 - Расширенный JSON для веб-визуализации                    |")
  (?princ "\n|  0 - Отмена                                                   |")
  (?princ "\n+---------------------------------------------------------------+")
  (?princ "\n\nВыбор: ")
  (setq Тип-Данных (getint))
  
  ; Специальная обработка для расширенного JSON
  (?catch "i: 3075 if Project-4.lsp " '; -L3075
    (if (= Тип-Данных 4) ; -L3076
      (?catch "i: 3077 progn Project-4.lsp " '; -L3077
        (progn ; -L3078
          (?princ "\n\nВведите имя файла (без расширения): ")
          (setq Имя-Файла (getstring))
          (?catch "i: 3081 if Project-4.lsp " '; -L3081
            (if (and Имя-Файла (/= Имя-Файла "")) ; -L3082
              (?catch "i: 3083 progn Project-4.lsp " '; -L3083
                (progn ; -L3084
                  (?catch "i: 3085 if Project-4.lsp " '; -L3085
                    (if (not (wcmatch Имя-Файла "*`.json")) ; -L3086
                      (setq Имя-Файла (strcat Имя-Файла ".json"))
                    ) ;end if L3088
                  ) ;end ?catch L3089
                  ; Загрузка модуля экспорта если нужно
                  (?catch "i: 3091 if Project-4.lsp " '; -L3091
                    (if (not (boundp 'Экспорт-Расширенный-JSON-Для-Веб-Визуализации)) ; -L3092
                      (?catch "i: 3093 if Project-4.lsp " '; -L3093
                        (if (findfile "Project-4-export-json.lsp") ; -L3094
                          (load "Project-4-export-json.lsp")
                        ) ;end if L3096
                      ) ;end ?catch L3097
                    ) ;end if L3098
                  ) ;end ?catch L3099
                  (?catch "i: 3100 if Project-4.lsp " '; -L3100
                    (if (boundp 'Экспорт-Расширенный-JSON-Для-Веб-Визуализации) ; -L3101
                      (?catch "i: 3102 progn Project-4.lsp " '; -L3102
                        (progn ; -L3103
                          (setq Результат (Экспорт-Расширенный-JSON-Для-Веб-Визуализации Имя-Файла))
                          (?catch "i: 3105 if Project-4.lsp " '; -L3105
                            (if Результат ; -L3106
                              (?princ "\n\n? Расширенный JSON для веб-визуализации экспортирован!")
                              (?princ "\n\n! Экспорт не выполнен")
                            ) ;end if L3109
                          ) ;end ?catch L3110
                        ) ;end progn L3111
                      ) ;end ?catch L3112
                      (?princ "\n\n! Функция экспорта расширенного JSON не найдена")
                    ) ;end if L3114
                  ) ;end ?catch L3115
                ) ;end progn L3116
              ) ;end ?catch L3117
              (?princ "\n\n! Имя файла не может быть пустым")
            ) ;end and L3119
          ) ;end ?catch L3120
        ) ;end progn L3121
      ) ;end ?catch L3122
      (?catch "i: 3123 if Project-4.lsp " '; -L3123
        (if (and Тип-Данных (> Тип-Данных 0) (<= Тип-Данных 3)) ; -L3124
          (?catch "i: 3125 progn Project-4.lsp " '; -L3125
            (progn ; -L3126
              ; Выбор формата экспорта
              (?princ "\n\n+---------------------------------------------------------------+")
              (?princ "\n| ФОРМАТ ЭКСПОРТА:                                              |")
              (?princ "\n+---------------------------------------------------------------+")
              (?princ "\n|  1 - JSON (JavaScript Object Notation)                        |")
              (?princ "\n|  2 - DOT (GraphViz для визуализации)                          |")
              (?princ "\n|  3 - XML (eXtensible Markup Language)                         |")
              (?princ "\n|  0 - Отмена                                                   |")
              (?princ "\n+---------------------------------------------------------------+")
              (?princ "\n\nВыбор: ")
              (setq Выбор (getint))
              
              (?catch "i: 3139 if Project-4.lsp " '; -L3139
                (if (and Выбор (> Выбор 0) (<= Выбор 3)) ; -L3140
                  (?catch "i: 3141 progn Project-4.lsp " '; -L3141
                    (progn ; -L3142
                      ; Запрос имени файла
                      (?princ "\n\nВведите имя файла (без расширения): ")
                      (setq Имя-Файла (getstring))
                      
                      (?catch "i: 3147 if Project-4.lsp " '; -L3147
                        (if (and Имя-Файла (/= Имя-Файла "")) ; -L3148
                          (?catch "i: 3149 progn Project-4.lsp " '; -L3149
                            (progn ; -L3150
                              ; Добавление расширения
                              (?catch "i: 3152 cond Project-4.lsp " '; -L3152
                                (cond ; -L3153
                                  ((= Выбор 1) (setq Имя-Файла (strcat Имя-Файла ".json"))) ; -L3154
                                  ((= Выбор 2) (setq Имя-Файла (strcat Имя-Файла ".dot"))) ; -L3155
                                  ((= Выбор 3) (setq Имя-Файла (strcat Имя-Файла ".xml"))) ; -L3156
                                ) ;end cond L3157
                              ) ;end ?catch L3158
                              
                              ; Выполнение экспорта
                              (setq Результат nil)
                              (?catch "i: 3162 cond Project-4.lsp " '; -L3162
                                (cond ; -L3163
                                  ; JSON
                                  ((= Выбор 1) ; -L3165
                                    (?catch "i: 3166 cond Project-4.lsp " '; -L3166
                                      (cond ; -L3167
                                        ((= Тип-Данных 1) ; -L3168
                                          (setq Результат (Экспорт-Continuation-JSON Имя-Файла))) ; -L3169
                                        ((= Тип-Данных 2) ; -L3170
                                          (setq Результат (Экспорт-Рабочая-Память-JSON Имя-Файла))) ; -L3171
                                        ((= Тип-Данных 3) ; -L3172
                                          (setq Результат (Экспорт-Полная-Структура-JSON Имя-Файла))) ; -L3173
                                      ) ;end cond L3174
                                    ) ;end ?catch L3175
                                  ) ;end cond case L3176
                                  ; DOT
                                  ((= Выбор 2) ; -L3178
                                    (?catch "i: 3179 cond Project-4.lsp " '; -L3179
                                      (cond ; -L3180
                                        ((= Тип-Данных 1) ; -L3181
                                          (setq Результат (Экспорт-Continuation-DOT Имя-Файла))) ; -L3182
                                        ((= Тип-Данных 2) ; -L3183
                                          (setq Результат (Экспорт-Рабочая-Память-DOT Имя-Файла))) ; -L3184
                                        ((= Тип-Данных 3) ; -L3185
                                          (?princ "\n! Экспорт полной структуры в DOT пока не реализован")
                                          (setq Результат nil)) ; -L3187
                                      ) ;end cond L3188
                                    ) ;end ?catch L3189
                                  ) ;end cond case L3190
                                  ; XML
                                  ((= Выбор 3) ; -L3192
                                    (?catch "i: 3193 cond Project-4.lsp " '; -L3193
                                      (cond ; -L3194
                                        ((= Тип-Данных 1) ; -L3195
                                          (setq Результат (Экспорт-Continuation-XML Имя-Файла))) ; -L3196
                                        ((= Тип-Данных 2) ; -L3197
                                          (setq Результат (Экспорт-Рабочая-Память-XML Имя-Файла))) ; -L3198
                                        ((= Тип-Данных 3) ; -L3199
                                          (setq Результат (Экспорт-Полная-Структура-XML Имя-Файла))) ; -L3200
                                      ) ;end cond L3201
                                    ) ;end ?catch L3202
                                  ) ;end cond case L3203
                                ) ;end cond L3204
                              ) ;end ?catch L3205
                              
                              (?catch "i: 3207 if Project-4.lsp " '; -L3207
                                (if Результат ; -L3208
                                  (?princ "\n\n? Экспорт выполнен успешно!")
                                  (?princ "\n\n! Экспорт не выполнен")
                                ) ;end if L3211
                              ) ;end ?catch L3212
                            ) ;end progn L3213
                          ) ;end ?catch L3214
                          (?princ "\n\n! Имя файла не может быть пустым")
                        ) ;end and L3216
                      ) ;end ?catch L3217
                    ) ;end progn L3218
                  ) ;end ?catch L3219
                  (?princ "\n\n? Операция отменена")
                ) ;end and L3221
              ) ;end ?catch L3222
            ) ;end progn L3223
          ) ;end ?catch L3224
          (?princ "\n\n? Операция отменена")
        ) ;end and L3226
      ) ;end ?catch L3227
    ) ;end if L3228
  ) ;end ?catch L3229
  
  (?princ "\n")
  (?princ)
)
(?log "L: 3234 Project-4.lsp c:Экспорт-Решения Переменная? ")

;===========================================================================
; УНИФИКАЦИЯ РОБИНСОНА (Robinson's Unification Algorithm)
;===========================================================================

; Глобальные переменные для унификации
(setq *Счетчик-Переменных* 0)           ; Счетчик для генерации переменных
(setq *Префикс-Переменных* "?")         ; Префикс для переменных унификации

(defun Переменная? (Терм)
  "Проверяет, является ли терм переменной
  
  Параметры:
    Терм - проверяемый терм
  
  Возвращает: T если переменная, nil если нет"
  
  (and (= (type Терм) 'SYM)
       (wcmatch (vl-symbol-name Терм) "?*"))
)
(?log "L: 3255 Project-4.lsp Переменная? Генерировать-Переменную ")

(defun Генерировать-Переменную (/ Имя)
  "Генерирует новую уникальную переменную
  
  Возвращает: символ новой переменной"
  
  (setq *Счетчик-Переменных* (+ *Счетчик-Переменных* 1)
        Имя (strcat *Префикс-Переменных* "VAR" (itoa *Счетчик-Переменных*))
  )
  (read Имя)
)
(?log "L: 3267 Project-4.lsp Генерировать-Переменную Occurs-Check ")

(defun Occurs-Check (Переменная Терм Подстановка)
  "Проверка вхождения переменной в терм (occurs check)
  
  Параметры:
    Переменная - проверяемая переменная
    Терм - терм для проверки
    Подстановка - текущая подстановка
  
  Возвращает: T если переменная входит в терм, nil если нет"
  
  (?catch "i: 3279 cond Project-4.lsp " '; -L3279
    (cond ; -L3280
      ; Если терм - та же переменная
      ((equal Переменная Терм) T) ; -L3282
      
      ; Если терм - другая переменная
      ((Переменная? Терм) ; -L3285
        (setq Значение (assoc Терм Подстановка))
        (?catch "i: 3287 if Project-4.lsp " '; -L3287
          (if Значение ; -L3288
            (Occurs-Check Переменная (cdr Значение) Подстановка)
            nil
          ) ;end if L3291
        ) ;end ?catch L3292
      ) ;end cond case L3293
      
      ; Если терм - список
      ((= (type Терм) 'LIST) ; -L3296
        (or (Occurs-Check Переменная (car Терм) Подстановка)
            (and (cdr Терм) (Occurs-Check Переменная (cdr Терм) Подстановка)) ; -L3298
        ) ;end or L3299
      ) ;end cond case L3300
      
      ; Для остальных случаев
      (T nil) ; -L3303
    ) ;end cond L3304
  ) ;end ?catch L3305
)
(?log "L: 3307 Project-4.lsp Occurs-Check Применить-Подстановку ")

(defun Применить-Подстановку (Терм Подстановка)
  "Применяет подстановку к терму
  
  Параметры:
    Терм - исходный терм
    Подстановка - подстановка для применения
  
  Возвращает: терм после применения подстановки"
  
  (?catch "i: 3318 cond Project-4.lsp " '; -L3318
    (cond ; -L3319
      ; Если терм - переменная
      ((Переменная? Терм) ; -L3321
        (setq Значение (assoc Терм Подстановка))
        (?catch "i: 3323 if Project-4.lsp " '; -L3323
          (if Значение ; -L3324
            (Применить-Подстановку (cdr Значение) Подстановка)
            Терм
          ) ;end if L3327
        ) ;end ?catch L3328
      ) ;end cond case L3329
      
      ; Если терм - список
      ((= (type Терм) 'LIST) ; -L3332
        (?catch "i: 3333 if Project-4.lsp " '; -L3333
          (if Терм ; -L3334
            (cons (Применить-Подстановку (car Терм) Подстановка)
                  (?catch "i: 3336 if Project-4.lsp " '; -L3336
                    (if (cdr Терм) ; -L3337
                      (Применить-Подстановку (cdr Терм) Подстановка)
                      nil
                    ) ;end if L3340
                  ) ;end ?catch L3341
            ) ;end cons L3342
            nil
          ) ;end if L3344
        ) ;end ?catch L3345
      ) ;end cond case L3346
      
      ; Для остальных типов
      (T Терм) ; -L3349
    ) ;end cond L3350
  ) ;end ?catch L3351
)
(?log "L: 3353 Project-4.lsp Применить-Подстановку Унифицировать ")

(defun Унифицировать (Терм1 Терм2 Подстановка)
  "Унифицирует два терма с использованием алгоритма Робинсона
  
  Параметры:
    Терм1 - первый терм
    Терм2 - второй терм
    Подстановка - текущая подстановка
  
  Возвращает: новую подстановку при успехе, nil при неудаче"
  
  (?catch "i: 3365 cond Project-4.lsp " '; -L3365
    (cond ; -L3366
      ; Если подстановка уже nil (ошибка)
      ((NULL Подстановка) nil) ; -L3368
      
      ; Если термы равны
      ((equal Терм1 Терм2) Подстановка) ; -L3371
      
      ; Если первый терм - переменная
      ((Переменная? Терм1) ; -L3374
        (Унифицировать-Переменную Терм1 Терм2 Подстановка)
      ) ;end cond case L3376
      
      ; Если второй терм - переменная
      ((Переменная? Терм2) ; -L3379
        (Унифицировать-Переменную Терм2 Терм1 Подстановка)
      ) ;end cond case L3381
      
      ; Если оба терма - списки
      ((and (= (type Терм1) 'LIST) (= (type Терм2) 'LIST)) ; -L3384
        (?catch "i: 3385 if Project-4.lsp " '; -L3385
          (if (and Терм1 Терм2) ; -L3386
            (Унифицировать 
              (cdr Терм1)
              (cdr Терм2)
              (Унифицировать (car Терм1) (car Терм2) Подстановка)
            ) ;end Унифицировать L3391
            ; Если один из списков пустой, а другой нет
            (?catch "i: 3393 if Project-4.lsp " '; -L3393
              (if (and (NULL Терм1) (NULL Терм2)) ; -L3394
                Подстановка
                nil
              ) ;end and L3397
            ) ;end ?catch L3398
          ) ;end and L3399
        ) ;end ?catch L3400
      ) ;end and L3401
      
      ; Для остальных случаев - неуспех
      (T nil) ; -L3404
    ) ;end cond L3405
  ) ;end ?catch L3406
)
(?log "L: 3408 Project-4.lsp Унифицировать Унифицировать-Переменную ")

(defun Унифицировать-Переменную (Переменная Терм Подстановка / Значение)
  "Унифицирует переменную с термом
  
  Параметры:
    Переменная - переменная для унификации
    Терм - терм для унификации
    Подстановка - текущая подстановка
  
  Возвращает: новую подстановку при успехе, nil при неудаче"
  
  ; Проверка, связана ли переменная
  (setq Значение (assoc Переменная Подстановка))
  (?catch "i: 3422 cond Project-4.lsp " '; -L3422
    (cond ; -L3423
      ; Если переменная уже связана
      (Значение ; -L3425
        (Унифицировать (cdr Значение) Терм Подстановка)
      ) ;end cond case L3427
      
      ; Если терм - переменная и она связана
      ((and (Переменная? Терм) (setq Значение (assoc Терм Подстановка))) ; -L3430
        (Унифицировать Переменная (cdr Значение) Подстановка)
      ) ;end and L3432
      
      ; Проверка на циклические структуры (occurs check)
      ((Occurs-Check Переменная Терм Подстановка) ; -L3435
        (?catch "i: 3436 if Project-4.lsp " '; -L3436
          (if *isDebug* ; -L3437
            (?princ (strcat "\n[Унификация] Ошибка: циклическая структура для " 
                          (vl-symbol-name Переменная)))
          ) ;end if L3440
        ) ;end ?catch L3441
        nil
      ) ;end cond case L3443
      
      ; Добавление новой связи
      (T ; -L3446
        (cons (cons Переменная Терм) Подстановка)
      ) ;end cond case L3448
    ) ;end cond L3449
  ) ;end ?catch L3450
)
(?log "L: 3452 Project-4.lsp Унифицировать-Переменную Переименовать-Переменные ")

(defun Переименовать-Переменные (Терм Отображение / Новая-Переменная)
  "Переименовывает переменные в терме
  
  Параметры:
    Терм - терм для переименования
    Отображение - отображение старых переменных на новые
  
  Возвращает: терм с переименованными переменными"
  
  (?catch "i: 3463 cond Project-4.lsp " '; -L3463
    (cond ; -L3464
      ; Если терм - переменная
      ((Переменная? Терм) ; -L3466
        (setq Значение (assoc Терм Отображение))
        (?catch "i: 3468 if Project-4.lsp " '; -L3468
          (if Значение ; -L3469
            (cdr Значение)
            (?catch "i: 3471 progn Project-4.lsp " '; -L3471
              (progn ; -L3472
                (setq Новая-Переменная (Генерировать-Переменную))
                (set Отображение (cons (cons Терм Новая-Переменная) (eval Отображение)))
                Новая-Переменная
              ) ;end progn L3476
            ) ;end ?catch L3477
          ) ;end if L3478
        ) ;end ?catch L3479
      ) ;end cond case L3480
      
      ; Если терм - список
      ((= (type Терм) 'LIST) ; -L3483
        (?catch "i: 3484 if Project-4.lsp " '; -L3484
          (if Терм ; -L3485
            (cons (Переименовать-Переменные (car Терм) Отображение)
                  (?catch "i: 3487 if Project-4.lsp " '; -L3487
                    (if (cdr Терм) ; -L3488
                      (Переименовать-Переменные (cdr Терм) Отображение)
                      nil
                    ) ;end if L3491
                  ) ;end ?catch L3492
            ) ;end cons L3493
            nil
          ) ;end if L3495
        ) ;end ?catch L3496
      ) ;end cond case L3497
      
      ; Для остальных типов
      (T Терм) ; -L3500
    ) ;end cond L3501
  ) ;end ?catch L3502
)
(?log "L: 3504 Project-4.lsp Переименовать-Переменные Сопоставить-С-Унификацией ")

;===========================================================================
; ИНТЕГРАЦИЯ УНИФИКАЦИИ С ВЫВОДОМ
;===========================================================================

; Глобальный индекс правил с переменными
(setq *Индекс-Правил-С-Переменными* nil)

(defun Сопоставить-С-Унификацией (Образец Факт)
  "Сопоставляет образец с фактом используя унификацию
  
  Параметры:
    Образец - образец с переменными
    Факт - конкретный факт
  
  Возвращает: подстановку при успехе, nil при неудаче"
  
  (Унифицировать Образец Факт '())
)
(?log "L: 3524 Project-4.lsp Сопоставить-С-Унификацией Найти-Факты-С-Унификацией ")

(defun Найти-Факты-С-Унификацией (Образец / Результаты Факт Подстановка)
  "Находит все факты, соответствующие образцу
  
  Параметры:
    Образец - образец с переменными
  
  Возвращает: список пар (факт . подстановка)"
  
  (setq Результаты nil)
  
  (?catch "i: 3536 if Project-4.lsp " '; -L3536
    (if (boundp '*Рабочая-Память*) ; -L3537
      (?catch "i: 3538 foreach Project-4.lsp " '; -L3538
        (foreach Факт *Рабочая-Память*
          (setq Подстановка (Сопоставить-С-Унификацией Образец (caddr Факт)))
          (?catch "i: 3541 if Project-4.lsp " '; -L3541
            (if Подстановка ; -L3542
              (setq Результаты (cons (cons Факт Подстановка) Результаты))
            ) ;end if L3544
          ) ;end ?catch L3545
        ) ;end foreach L3546
      ) ;end ?catch L3547
    ) ;end if L3548
  ) ;end ?catch L3549
  
  (reverse Результаты)
)
(?log "L: 3553 Project-4.lsp Найти-Факты-С-Унификацией Создать-Точку-Выбора ")

;===========================================================================
; BACKTRACKING - Механизм отката
;===========================================================================

; Глобальные переменные для backtracking
(setq *Стек-Выбора* nil)              ; Стек точек выбора
(setq *История-Backtrack* nil)        ; История откатов

(defun Создать-Точку-Выбора (Альтернативы Состояние)
  "Создает точку выбора для backtracking
  
  Параметры:
    Альтернативы - список альтернативных путей вывода
    Состояние - текущее состояние для восстановления
  
  Возвращает: ID точки выбора"
  
  (?catch "i: 3572 setq Project-4.lsp " '; -L3572
    (setq ID (+ (length *Стек-Выбора*) 1)
          Точка (list
            (cons 'ID ID)
            (cons 'Альтернативы Альтернативы)
            (cons 'Состояние (Глубокое-Копирование Состояние))
            (cons 'Время (getvar "DATE"))
          )
    )
  )
  
  (setq *Стек-Выбора* (cons Точка *Стек-Выбора*))
  
  (?catch "i: 3585 if Project-4.lsp " '; -L3585
    (if *isDebug* ; -L3586
      (?princ (strcat "\n[Backtracking] Создана точка выбора #" (itoa ID)))
    ) ;end if L3588
  ) ;end ?catch L3589
  
  ID
)
(?log "L: 3593 Project-4.lsp Создать-Точку-Выбора Откатить-К-Точке-Выбора ")

(defun Откатить-К-Точке-Выбора (/ Точка)
  "Откатывает к последней точке выбора
  
  Возвращает: точку выбора или nil если стек пуст"
  
  (?catch "i: 3600 if Project-4.lsp " '; -L3600
    (if *Стек-Выбора* ; -L3601
      (?catch "i: 3602 progn Project-4.lsp " '; -L3602
        (progn ; -L3603
          (?catch "i: 3604 setq Project-4.lsp " '; -L3604
            (setq Точка (car *Стек-Выбора*)
                  *Стек-Выбора* (cdr *Стек-Выбора*)
            )
          ) ;end ?catch L3608
          
          ; Восстановление состояния
          (setq Состояние (cdr (assoc 'Состояние Точка)))
          (?catch "i: 3612 if Project-4.lsp " '; -L3612
            (if Состояние ; -L3613
              (setq *Рабочая-Память* (cdr (assoc 'Память Состояние)))
            ) ;end if L3615
          ) ;end ?catch L3616
          
          ; История
          (?catch "i: 3619 setq Project-4.lsp " '; -L3619
            (setq *История-Backtrack* 
              (cons (list 'BACKTRACK (cdr (assoc 'ID Точка)) (getvar "DATE"))
                    *История-Backtrack*)
            )
          ) ;end ?catch L3624
          
          (?catch "i: 3626 if Project-4.lsp " '; -L3626
            (if *isDebug* ; -L3627
              (?princ (strcat "\n[Backtracking] Откат к точке #" 
                            (itoa (cdr (assoc 'ID Точка)))))
            ) ;end if L3630
          ) ;end ?catch L3631
          
          Точка
        ) ;end progn L3634
      ) ;end ?catch L3635
      (?catch "i: 3636 progn Project-4.lsp " '; -L3636
        (progn ; -L3637
          (?catch "i: 3638 if Project-4.lsp " '; -L3638
            (if *isDebug* ; -L3639
              (?princ "\n[Backtracking] Нет точек выбора")
            ) ;end if L3641
          ) ;end ?catch L3642
          nil
        ) ;end progn L3644
      ) ;end ?catch L3645
    ) ;end if L3646
  ) ;end ?catch L3647
)
(?log "L: 3649 Project-4.lsp Откатить-К-Точке-Выбора Очистить-Backtracking ")

(defun Очистить-Backtracking ()
  "Очищает стек backtracking"
  (?catch "i: 3653 setq Project-4.lsp " '; -L3653
    (setq *Стек-Выбора* nil
          *История-Backtrack* nil
    )
  )
  (?catch "i: 3658 if Project-4.lsp " '; -L3658
    (if *isDebug* ; -L3659
      (?princ "\n[Backtracking] Стек очищен")
    ) ;end if L3661
  ) ;end ?catch L3662
)
(?log "L: 3664 Project-4.lsp Очистить-Backtracking nil ")


(?princ "\r[Project-4.2] - Loaded")
